' ============================================================
' UPDATE 2026-08-15: CUSTOM iPROPERTY + EXCEL GRID
' - Tạo Custom iProperty mới ngay từ bảng BOM; chỉ tạo trong Part khi COMMIT.
' - Part đã có property => update; Part chưa có => tự PropertySet.Add.
' - UNIVERSAL CONTROL V1.1 COMPILE FIX: Material/Appearance + Sheet Metal Rule/Thickness/Material source/Unfold Rule.
' - Ctrl+C/Ctrl+V vùng ô; paste 1 giá trị cho nhiều ô; Fill Handle kéo chuột.
' - Atomic rollback/Undo xóa Custom iProperty vừa tạo nếu trước đó chưa tồn tại.
' ============================================================
' TÊN: Quản Lý BOM
' CÔNG DỤNG: Quét, lọc, sửa, kiểm tra và xuất Excel dữ liệu BOM/iProperty của Assembly.
' TÊN CŨ: BOM_3D.iLogicVb
' PHÂN LOẠI: 3D
' ============================================================

' ============================================================================
' HIEU INVENTOR AUTOMATION SUITE - 02_BOM_BALLOON_MANAGER_PRO
' Production BOM core + Stock Number sorting + future Drawing BOM/Balloon sync.
' MASTER CONSOLIDATION BUILD - 2026-07-30
'
' ABSORBED SOURCES:
'   - BOM_TOOL_PRO
'   - sort-part-lists-by-stock-number
'   - balloon-update Beta
'   - stock-number-to-balloon
'
' NOTE: The primary production engine remains executable. Additional source
' engines are embedded at the end as disabled reference modules to prevent
' duplicate Sub Main/Class/Imports compile collisions during staged integration.
' ============================================================================
'====================================================================
' BOM TOOL PRO BY HIẾU - MERGED RELEASE
' INTEGRATION: SMART STOCK NUMBER SORT (from sort-part-lists-by-stock-number.vb concept)
' MERGE: V23.1 COMPILE FIX + V29 SAFE ASSEMBLY SWITCH
' Inventor 2025 / iLogic
' Base: V29 Safe Assembly Switch (superset branch)
' Preserves shared Production Transaction / Performance / Validation core
'====================================================================

' USER REPORT IMPLEMENTATION - UI/UX PROFESSIONALIZATION + COMMAND ARCHITECTURE + SECONDARY FORMS
' BOM TOOL PRO MAX 10.3 SAFE ASSEMBLY SWITCH - FINAL HARDENING / RECOVERY / MANUFACTURING 2.0
' Upgraded from BOM TOOL PRO BY HIẾU (14)
' Inventor 2025 / iLogic compatibility baseline
' BOM TOOL PRO BY HIẾU 14.1 - PHASE 2 PRODUCTION TRANSACTION ENGINE
' Atomic Commit / Selected Commit / Operation Undo-Redo / Partial Commit Report / Batch Save Changed Docs
'====================================================================
' BOM TOOL PRO BY HIẾU - V13.3 PERFORMANCE CORE 2.0 
'====================================================================

'====================================================================
' V20 PHASE 1 CORE PERFORMANCE
' - Change Signature: path + LastWriteTimeUtc + FileSize + document Dirty
' - Smart Incremental Refresh: UNCHANGED lấy cache, CHANGED mới đọc lại
' - Root Assembly change detector: tự chuyển Full Reload để bắt NEW/REMOVED/QTY
' - Cache hit/miss + signature check + refresh timing monitor
' - Giữ Lazy Feature/Thumbnail engine hiện có
'====================================================================

AddReference "System.Windows.Forms.dll"
AddReference "System.Drawing.dll"

Imports System
Imports System.Collections.Generic
Imports System.Data
Imports System.Text
Imports System.Text.RegularExpressions
Imports System.Diagnostics
Imports System.Runtime.InteropServices
Imports Inventor

Imports IOPath = System.IO.Path
Imports WinFormsApplication = System.Windows.Forms.Application
Imports Form = System.Windows.Forms.Form
Imports Label = System.Windows.Forms.Label
Imports Button = System.Windows.Forms.Button
Imports TextBox = System.Windows.Forms.TextBox
Imports CheckBox = System.Windows.Forms.CheckBox
Imports CheckedListBox = System.Windows.Forms.CheckedListBox
Imports ListBox = System.Windows.Forms.ListBox
Imports GroupBox = System.Windows.Forms.GroupBox
Imports ProgressBar = System.Windows.Forms.ProgressBar
Imports SaveFileDialog = System.Windows.Forms.SaveFileDialog
Imports OpenFileDialog = System.Windows.Forms.OpenFileDialog
Imports DialogResult = System.Windows.Forms.DialogResult
Imports MessageBox = System.Windows.Forms.MessageBox
Imports MessageBoxButtons = System.Windows.Forms.MessageBoxButtons
Imports MessageBoxIcon = System.Windows.Forms.MessageBoxIcon
Imports FormStartPosition = System.Windows.Forms.FormStartPosition
Imports SelectionMode = System.Windows.Forms.SelectionMode
Imports FlatStyle = System.Windows.Forms.FlatStyle
Imports ProgressBarStyle = System.Windows.Forms.ProgressBarStyle
Imports DataGridView = System.Windows.Forms.DataGridView
Imports DataGridViewRow = System.Windows.Forms.DataGridViewRow
Imports DataGridViewColumn = System.Windows.Forms.DataGridViewColumn
Imports DataGridViewCell = System.Windows.Forms.DataGridViewCell
Imports DataGridViewAutoSizeColumnMode = System.Windows.Forms.DataGridViewAutoSizeColumnMode
Imports HorizontalAlignment = System.Windows.Forms.HorizontalAlignment
Imports TextFormatFlags = System.Windows.Forms.TextFormatFlags
Imports Keys = System.Windows.Forms.Keys
Imports Control = System.Windows.Forms.Control
Imports DataGridViewAutoSizeColumnsMode = System.Windows.Forms.DataGridViewAutoSizeColumnsMode
Imports DataGridViewSelectionMode = System.Windows.Forms.DataGridViewSelectionMode
Imports ContextMenuStrip = System.Windows.Forms.ContextMenuStrip
Imports ToolStripMenuItem = System.Windows.Forms.ToolStripMenuItem
Imports ToolStripSeparator = System.Windows.Forms.ToolStripSeparator
Imports Panel = System.Windows.Forms.Panel
Imports DockStyle = System.Windows.Forms.DockStyle
Imports AnchorStyles = System.Windows.Forms.AnchorStyles
Imports FormClosedEventArgs = System.Windows.Forms.FormClosedEventArgs
Imports MouseEventArgs = System.Windows.Forms.MouseEventArgs
Imports DataGridViewCellMouseEventArgs = System.Windows.Forms.DataGridViewCellMouseEventArgs
Imports DataGridViewCellEventArgs = System.Windows.Forms.DataGridViewCellEventArgs
Imports DataGridViewCellCancelEventArgs = System.Windows.Forms.DataGridViewCellCancelEventArgs
Imports Clipboard = System.Windows.Forms.Clipboard
Imports ComboBox = System.Windows.Forms.ComboBox
Imports ComboBoxStyle = System.Windows.Forms.ComboBoxStyle
Imports ScrollBars = System.Windows.Forms.ScrollBars
Imports MouseButtons = System.Windows.Forms.MouseButtons
Imports DragDropEffects = System.Windows.Forms.DragDropEffects
Imports DragEventArgs = System.Windows.Forms.DragEventArgs
Imports CheckState = System.Windows.Forms.CheckState
Imports Color = System.Drawing.Color
Imports Point = System.Drawing.Point
Imports Size = System.Drawing.Size
Imports Font = System.Drawing.Font
Imports FontStyle = System.Drawing.FontStyle
Imports ContentAlignment = System.Drawing.ContentAlignment
Imports Rectangle = System.Drawing.Rectangle
Imports Image = System.Drawing.Image
Imports Bitmap = System.Drawing.Bitmap
Imports PictureBox = System.Windows.Forms.PictureBox
Imports SplitContainer = System.Windows.Forms.SplitContainer
Imports Orientation = System.Windows.Forms.Orientation
Imports DataGridViewImageCellLayout = System.Windows.Forms.DataGridViewImageCellLayout

'====================================================================
' BOM TOOL PRO BY HIẾU - V9 

'####################################################################
' BOM TOOL PRO - MASTER STRUCTURE MAP
'####################################################################
' 01. PROGRAM ENTRY / MAIN CONTROLLER
' 02. VIEWER CALLBACKS / DATA BRIDGE
' 03. SCAN CONTROL / CANCELLATION
' 04. INVENTOR ASSEMBLY SCAN ENGINE
' 05. IPROPERTY READ ENGINE
' 06. EXCEL EXPORT ENGINE
' 07. ASSEMBLY EXPORT DATA MODELS
' 08. COMMON UTILITIES / FORMAT / COM RELEASE
' 09. CORE DATA CACHE / GEOMETRY
' 10. PRIMARY BOM DATA MODELS
' 11. PROPERTY SELECTION UI
' 12. PROGRESS / CANCEL UI
' 13. UNIT ENGINE
' 14. EDIT HISTORY / VIEWER REGISTRY
' 15. MAIN BOM VIEWER FORM
'     15.01 Constructor & Interface
'     15.02 Ribbon & Quick Access
'     15.03 Status Bar & Context Menu
'     15.04 Grid Columns & Row Rendering
'     15.05 Assembly Filter & Search
'     15.06 Grid Selection & Mouse Events
'     15.07 Cell Editing & Undo/Redo
'     15.08 Group / Mark / Layout
'     15.09 Part & Drawing Interaction
'     15.10 Excel-like Grid Commands
'     15.11 Where Used & Occurrence Helpers
'     15.12 Inventor Commands
'     15.13 Refresh / Calculator / Export
' 16. ADD PROPERTY FORM
' 17. COLUMN MANAGER FORM
' 18. DASHBOARD FORM
' 19. PROJECT CHECK FORM
' 20. CALCULATOR / ANALYTICS FORM
' 21. ON-DEMAND FEATURE ENGINE / THUMBNAIL / PREVIEW
'####################################################################
' MAINTENANCE RULES
' - Không đặt code giao diện vào Scan Engine.
' - Không gọi Inventor từ Search/Filter nếu dữ liệu đã có trong Cache.
' - Không thêm Catch rỗng tại khu vực quan trọng.
' - Mỗi chức năng mới phải được đặt đúng SECTION và SUBSECTION.
' - Giữ Main ngắn, chỉ điều phối và xử lý lỗi cấp cao.
'####################################################################

'
' Chức năng:
'   - Chạy trong Assembly (.iam)
'   - Quét kiểu Parts Only
'   - Bung toàn bộ Sub-Assembly thành Part
'   - Gộp Part theo đường dẫn file và cộng số lượng
'   - Ghi Part nằm trong Assembly nào
'   - Chỉ quét tên iProperty để dựng danh sách chọn
'   - Sau khi chọn chỉ đọc đúng giá trị iProperty đã chọn
'   - Có Progress Bar và nút Hủy
'   - Xuất Excel hoàn chỉnh, không cần căn chỉnh lại
'   - Không dùng ThisApplication.ScreenUpdating nên không làm ảnh hưởng
'     hiển thị các document khác đang mở
'====================================================================


'####################################################################
' SECTION 01 - PROGRAM ENTRY / MAIN CONTROLLER
' Kiểm tra môi trường, khởi tạo, điều phối luồng chính và xử lý lỗi cấp cao.
'####################################################################

Sub Main()

    '==================================================================
    ' SINGLE INSTANCE + ASSEMBLY IDENTITY GUARD
    ' IMPORTANT: this executes BEFORE scan/reset/property/progress.
    '==================================================================
    Dim entryActivePath As String = ""
    Try
        If ThisApplication.ActiveDocument IsNot Nothing AndAlso
           ThisApplication.ActiveDocument.DocumentType = DocumentTypeEnum.kAssemblyDocumentObject Then
            entryActivePath = CType(ThisApplication.ActiveDocument, AssemblyDocument).FullFileName
        End If
    Catch
        entryActivePath = ""
    End Try

    If BomViewerRegistry.HasActiveViewer() Then
        If BomViewerRegistry.IsSameAssembly(entryActivePath) Then
            ' CASE B: SAME ASSEMBLY.
            ' Absolutely no refresh/reload/reset is allowed.
            BomViewerRegistry.TryActivateExistingViewer()
            Exit Sub
        End If

        ' CASE C: VIEWER EXISTS BUT ACTIVE ASSEMBLY IS DIFFERENT.
        ' Ask before touching the current BOM.
        If String.IsNullOrWhiteSpace(entryActivePath) Then
            BomViewerRegistry.TryActivateExistingViewer()
            Exit Sub
        End If

        Dim switchDecision As BomAssemblySwitchDecision = BomAssemblySwitchDecision.Cancel
        Using switchForm As New BomAssemblySwitchForm( _
            BomViewerRegistry.CurrentAssemblyPath, _
            entryActivePath, _
            BomViewerRegistry.CurrentViewer.PendingChangeCount)
            switchForm.ShowDialog(BomViewerRegistry.CurrentViewer)
            switchDecision = switchForm.Decision
        End Using

        If switchDecision = BomAssemblySwitchDecision.KeepCurrent Then
            BomViewerRegistry.TryActivateExistingViewer()
            Exit Sub
        ElseIf switchDecision <> BomAssemblySwitchDecision.LoadNew Then
            Exit Sub
        End If

        ' Second safety layer: pending transaction must be explicitly resolved.
        If BomViewerRegistry.CurrentViewer.PendingChangeCount > 0 Then
            If Not BomViewerRegistry.CurrentViewer.ResolvePendingBeforeAssemblySwitch() Then
                BomViewerRegistry.TryActivateExistingViewer()
                Exit Sub
            End If
        End If

        ' Do NOT close the old viewer here.
        ' Main continues and scans the new Assembly into temporary/local data.
        ' Existing viewer stays intact until scan succeeds completely.
    Else
        ' Clean stale reference, if any.
        BomSingleInstanceManager.TryActivateExisting()
    End If

    BomLogger.Reset()
    BomPerformanceCounters.Reset()
    Dim mainWatch As Stopwatch = Stopwatch.StartNew()
    Dim progressForm As BomProgressForm = Nothing

    Try
        '==============================================================
        ' KIỂM TRA DOCUMENT
        '==============================================================
        If ThisApplication.ActiveDocument Is Nothing Then
            MessageBox.Show( _
                "Không có tài liệu nào đang mở.", _
                "BOM TOOL PRO", _
                MessageBoxButtons.OK, _
                MessageBoxIcon.Warning)
            Exit Sub
        End If

        If ThisApplication.ActiveDocument.DocumentType <> _
           DocumentTypeEnum.kAssemblyDocumentObject Then

            MessageBox.Show( _
                "Rule này chỉ chạy trong môi trường Assembly (.iam).", _
                "BOM TOOL PRO", _
                MessageBoxButtons.OK, _
                MessageBoxIcon.Warning)
            Exit Sub
        End If

        Dim targetAssembly As AssemblyDocument = _
            CType(ThisApplication.ActiveDocument, AssemblyDocument)

        If String.IsNullOrWhiteSpace(targetAssembly.FullFileName) Then
            MessageBox.Show( _
                "Hãy lưu file Assembly trước khi xuất BOM.", _
                "BOM TOOL PRO", _
                MessageBoxButtons.OK, _
                MessageBoxIcon.Warning)
            Exit Sub
        End If

        '==============================================================
        ' HIỂN THỊ PROGRESS FORM
        '==============================================================
        progressForm = New BomProgressForm()
        progressForm.Show()
        progressForm.SetProgress(2, "Đang khởi tạo BOM Tool...")
        WinFormsApplication.DoEvents()

        '==============================================================
        ' QUÉT CÂY ASSEMBLY
        '==============================================================
        Dim partDictionary As New Dictionary( _
            Of String, PartBomItem)(StringComparer.OrdinalIgnoreCase)

        Dim rootAssemblyName As String = _
            GetDocumentPartNumberOrFileName(targetAssembly)

        Dim scannedOccurrenceCount As Integer = 0

        progressForm.SetProgress(8, "Đang quét cấu trúc Assembly...")

        ScanOccurrences( _
            targetAssembly.ComponentDefinition.Occurrences, _
            rootAssemblyName, _
            rootAssemblyName, _
            partDictionary, _
            progressForm, _
            scannedOccurrenceCount)

        CheckCancel(progressForm)

        If partDictionary.Count = 0 Then
            progressForm.Close()
            progressForm.Dispose()
            progressForm = Nothing

            MessageBox.Show( _
                "Không tìm thấy Part hợp lệ trong Assembly." & vbCrLf & _
                "Các component đang Suppress sẽ bị bỏ qua.", _
                "BOM TOOL PRO", _
                MessageBoxButtons.OK, _
                MessageBoxIcon.Information)
            Exit Sub
        End If

        progressForm.SetProgress(30, _
            "Đã quét xong cấu trúc Assembly." & vbCrLf & _
            "Component đã kiểm tra: " & scannedOccurrenceCount.ToString() & vbCrLf & _
            "Loại Part tìm thấy: " & partDictionary.Count.ToString())

        '==============================================================
        ' CHUYỂN DICTIONARY THÀNH LIST
        '==============================================================
        Dim bomItems As New List(Of PartBomItem)

        For Each pair As KeyValuePair(Of String, PartBomItem) In partDictionary
            Dim cachedItem As PartBomItem = pair.Value
            cachedItem.SearchBlob = (cachedItem.FileName & "|" & cachedItem.FilePath & "|" & cachedItem.PartNumber & "|" & cachedItem.Description & "|" & cachedItem.Material & "|" & cachedItem.Vendor & "|" & cachedItem.Revision & "|" & cachedItem.StockNumber & "|" & cachedItem.Project & "|" & cachedItem.Category & "|" & cachedItem.GetParentAssemblyText()).ToUpperInvariant()
            bomItems.Add(cachedItem)
        Next

        bomItems.Sort(AddressOf CompareBomItems)

        '==============================================================
        ' CHỈ QUÉT TÊN IPROPERTY
        ' Không đọc Value ở bước này
        '==============================================================
        Dim propertyDictionary As New Dictionary( _
            Of String, PropertyColumnInfo)(StringComparer.OrdinalIgnoreCase)

        Dim propertyScanIndex As Integer = 0
        Dim totalParts As Integer = bomItems.Count

        progressForm.SetProgress(34, "Đang lập danh sách tên iProperty...")

        For Each item As PartBomItem In bomItems
            CheckCancel(progressForm)
            propertyScanIndex += 1

            If item.Document IsNot Nothing Then
                ScanDocumentPropertyNames(item.Document, propertyDictionary)
            End If

            If propertyScanIndex Mod 20 = 0 OrElse propertyScanIndex = totalParts Then
                Dim propertyProgress As Integer = 34

                If totalParts > 0 Then
                    propertyProgress = 34 + CInt( _
                        (CDbl(propertyScanIndex) / CDbl(totalParts)) * 16)
                End If

                progressForm.SetProgress( _
                    Math.Min(propertyProgress, 50), _
                    "Đang lập danh sách iProperty..." & vbCrLf & _
                    propertyScanIndex.ToString() & " / " & totalParts.ToString() & " Part")
            End If
        Next

        Dim availableProperties As New List(Of PropertyColumnInfo)

        For Each pair As KeyValuePair(Of String, PropertyColumnInfo) In propertyDictionary
            availableProperties.Add(pair.Value)
        Next

        availableProperties.Sort(AddressOf ComparePropertyColumns)

        '==============================================================
        ' HIỆN FORM CHỌN CỘT
        '==============================================================
        progressForm.SetProgress(52, _
            "Đã lập xong danh sách iProperty." & vbCrLf & _
            "Đang mở cửa sổ chọn cột...")
        progressForm.Hide()

        Dim selectionForm As New BomPropertySelectionForm( _
            availableProperties, _
            bomItems.Count)

        Dim formResult As DialogResult = selectionForm.ShowDialog()

        If formResult <> DialogResult.OK Then
            progressForm.Close()
            progressForm.Dispose()
            progressForm = Nothing
            Exit Sub
        End If

        Dim selectedProperties As List(Of PropertyColumnInfo) = _
            selectionForm.SelectedProperties

        Dim includeFileName As Boolean = selectionForm.IncludeFileName
        Dim includeFilePath As Boolean = selectionForm.IncludeFilePath
        Dim includeParentAssembly As Boolean = selectionForm.IncludeParentAssembly
        Dim openExcelAfterExport As Boolean = selectionForm.OpenExcelAfterExport
        Dim selectedScanMode As BomScanMode = selectionForm.SelectedScanMode

        '==============================================================
        ' SAU KHI CHỌN MỚI ĐỌC ĐÚNG PROPERTY ĐƯỢC CHỌN
        '==============================================================
        progressForm.Show()
        progressForm.SetProgress(55, _
            "Đang đọc đúng các iProperty đã chọn..." & vbCrLf & _
            "Số cột iProperty: " & selectedProperties.Count.ToString())

        ReadSelectedPropertiesOnly( _
            bomItems, _
            selectedProperties, _
            progressForm)

        CheckCancel(progressForm)

        '==============================================================
        ' ĐÓNG PROGRESS VÀ MỞ BOM VIEWER KHÔNG KHÓA INVENTOR
        '==============================================================
        progressForm.SetProgress(100, "Đã nạp xong dữ liệu BOM.")
        WinFormsApplication.DoEvents()
        progressForm.Close()
        progressForm.Dispose()
        progressForm = Nothing

        'SAFE SWITCH:
        'At this point the NEW assembly has already scanned successfully.
        'The old Viewer/Data Model has intentionally remained untouched.

        Dim existingViewer As BomViewerForm = Nothing
        If BomViewerRegistry.HasActiveViewer() Then existingViewer = BomViewerRegistry.CurrentViewer

        Dim exportCallback As System.Action(Of List(Of PartBomItem)) = _
            Sub(rowsToExport As List(Of PartBomItem))
                ExportRowsFromViewer( _
                    targetAssembly, _
                    rowsToExport, _
                    selectedProperties, _
                    includeFileName, _
                    includeFilePath, _
                    includeParentAssembly, _
                    openExcelAfterExport)
            End Sub

        Dim refreshCallback As System.Action(Of List(Of PartBomItem)) = _
            Sub(rowsToRefresh As List(Of PartBomItem))
                RefreshRowsFromViewer(rowsToRefresh, selectedProperties)
            End Sub

        'Nạp BOM từ đúng document đang Active trong Inventor.
        'Viewer cũ chỉ bị thay sau khi Assembly mới đã quét thành công.
        Dim loadBomCallback As System.Action = _
            Sub()
                Try
                    If ThisApplication.ActiveDocument Is Nothing Then
                        MessageBox.Show( _
                            "Không có tài liệu nào đang mở.", _
                            "LOAD BOM", _
                            MessageBoxButtons.OK, _
                            MessageBoxIcon.Warning)
                        Exit Sub
                    End If

                    If ThisApplication.ActiveDocument.DocumentType <> _
                       DocumentTypeEnum.kAssemblyDocumentObject Then

                        MessageBox.Show( _
                            "Đây không phải file lắp ráp (.iam)." & vbCrLf & _
                            "Hãy Active một Assembly rồi nhấn LOAD BOM lại.", _
                            "LOAD BOM", _
                            MessageBoxButtons.OK, _
                            MessageBoxIcon.Warning)
                        Exit Sub
                    End If

                    Dim activeAsm As AssemblyDocument = _
                        CType(ThisApplication.ActiveDocument, AssemblyDocument)

                    If String.Equals( _
                        activeAsm.FullFileName, _
                        targetAssembly.FullFileName, _
                        StringComparison.OrdinalIgnoreCase) Then

                        Dim sameResult As DialogResult = MessageBox.Show( _
                            "Assembly đang Active chính là BOM hiện tại:" & vbCrLf & _
                            activeAsm.DisplayName & vbCrLf & vbCrLf & _
                            "Bạn có muốn nạp lại BOM này không?", _
                            "LOAD BOM", _
                            MessageBoxButtons.YesNo, _
                            MessageBoxIcon.Question)

                        If sameResult <> DialogResult.Yes Then Exit Sub
                    Else
                        Dim replaceResult As DialogResult = MessageBox.Show( _
                            "BOM hiện tại:" & vbCrLf & _
                            targetAssembly.DisplayName & vbCrLf & vbCrLf & _
                            "Assembly đang Active:" & vbCrLf & _
                            activeAsm.DisplayName & vbCrLf & vbCrLf & _
                            "Bạn có muốn thay BOM hiện tại bằng Assembly đang Active không?", _
                            "LOAD BOM", _
                            MessageBoxButtons.YesNo, _
                            MessageBoxIcon.Question)

                        If replaceResult <> DialogResult.Yes Then Exit Sub
                    End If

                    MessageBox.Show( _
                        "Không gọi lại External Rule từ bên trong Viewer." & vbCrLf & _
                        "Hãy Active Assembly cần chuyển và chạy BOM Tool; hệ thống sẽ xử lý Safe Assembly Switch.", _
                        "ASSEMBLY SWITCH", _
                        MessageBoxButtons.OK, _
                        MessageBoxIcon.Information)

                Catch ex As Exception
                    MessageBox.Show( _
                        "Không thể Load BOM từ Assembly đang Active." & vbCrLf & _
                        ex.Message, _
                        "LOAD BOM", _
                        MessageBoxButtons.OK, _
                        MessageBoxIcon.Error)
                End Try
            End Sub

        BomPerformanceCounters.InitialLoadMs = mainWatch.ElapsedMilliseconds

        If existingViewer IsNot Nothing AndAlso Not existingViewer.IsDisposed Then
            'REUSE EXISTING VIEWER. No close/dispose/flicker.
            existingViewer.ReplaceAssemblyData( _
                targetAssembly.FullFileName, _
                GetDocumentPartNumberOrFileName(targetAssembly), _
                bomItems, _
                selectedProperties, _
                includeFileName, _
                includeFilePath, _
                includeParentAssembly, _
                exportCallback, _
                refreshCallback, _
                loadBomCallback, _
                selectedScanMode)

            BomViewerRegistry.UpdateAssembly(targetAssembly.FullFileName)
            BomLogger.Info("ASSEMBLY_SWITCH", "Switched Viewer safely to: " & targetAssembly.FullFileName)
            existingViewer.BringToFront()
            existingViewer.Activate()
        Else
            Dim viewer As New BomViewerForm( _
                ThisApplication, _
                targetAssembly.FullFileName, _
                GetDocumentPartNumberOrFileName(targetAssembly), _
                bomItems, _
                selectedProperties, _
                includeFileName, _
                includeFilePath, _
                includeParentAssembly, _
                exportCallback, _
                refreshCallback, _
                loadBomCallback, _
                selectedScanMode)

            BomViewerRegistry.Register(viewer, targetAssembly.FullFileName)

            AddHandler viewer.FormClosed, _
                Sub(sender As Object, e As FormClosedEventArgs)
                    BomViewerRegistry.Unregister(viewer)
                End Sub

            BomLogger.Info("MAIN", "BOM loaded: " & bomItems.Count.ToString() & " unique Part in " & mainWatch.ElapsedMilliseconds.ToString() & " ms")
            viewer.Show()
            viewer.BringToFront()
        End If

    Catch ex As OperationCanceledException

        If progressForm IsNot Nothing Then
            Try
                progressForm.Close()
                progressForm.Dispose()
            Catch
            End Try
        End If

        MessageBox.Show( _
            "Đã hủy quá trình xuất BOM.", _
            "BOM TOOL PRO", _
            MessageBoxButtons.OK, _
            MessageBoxIcon.Information)

    Catch ex As Exception

        If progressForm IsNot Nothing Then
            Try
                progressForm.Close()
                progressForm.Dispose()
            Catch
            End Try
        End If

        MessageBox.Show( _
            "Không thể xuất BOM." & vbCrLf & vbCrLf & _
            "Chi tiết lỗi:" & vbCrLf & ex.Message, _
            "BOM TOOL PRO", _
            MessageBoxButtons.OK, _
            MessageBoxIcon.Error)

    End Try

End Sub


'====================================================================
' XUẤT DỮ LIỆU TỪ BOM VIEWER
'====================================================================

'####################################################################
' SECTION 02 - VIEWER CALLBACKS / DATA BRIDGE
' Các callback giữa Main, Viewer, Refresh và Export.
'####################################################################

Sub ExportRowsFromViewer( _
    ByVal targetAssembly As AssemblyDocument, _
    ByVal rowsToExport As List(Of PartBomItem), _
    ByVal selectedProperties As List(Of PropertyColumnInfo), _
    ByVal includeFileName As Boolean, _
    ByVal includeFilePath As Boolean, _
    ByVal includeParentAssembly As Boolean, _
    ByVal openExcelAfterExport As Boolean)

    If rowsToExport Is Nothing OrElse rowsToExport.Count = 0 Then
        MessageBox.Show("Không có dòng dữ liệu nào để xuất.", "BOM TOOL PRO", MessageBoxButtons.OK, MessageBoxIcon.Information)
        Exit Sub
    End If

    Dim defaultFileName As String = _
        IOPath.GetFileNameWithoutExtension(targetAssembly.FullFileName) & _
        "_PARTS_ONLY_BOM_" & DateTime.Now.ToString("yyyyMMdd_HHmmss") & ".xlsx"

    Dim saveDialog As New SaveFileDialog()
    saveDialog.Title = "Lưu Parts Only BOM"
    saveDialog.Filter = "Excel Workbook (*.xlsx)|*.xlsx"
    saveDialog.FileName = defaultFileName
    saveDialog.InitialDirectory = IOPath.GetDirectoryName(targetAssembly.FullFileName)
    saveDialog.OverwritePrompt = True
    saveDialog.AddExtension = True
    saveDialog.DefaultExt = "xlsx"

    If saveDialog.ShowDialog() <> DialogResult.OK Then Exit Sub

    Dim progress As New BomProgressForm()
    Try
        progress.Show()
        progress.SetProgress(76, "Đang chuẩn bị dữ liệu xuất Excel...")

        ExportBomToExcel( _
            targetAssembly, _
            rowsToExport, _
            selectedProperties, _
            includeFileName, _
            includeFilePath, _
            includeParentAssembly, _
            saveDialog.FileName, _
            openExcelAfterExport, _
            progress)

        progress.Close()
        progress.Dispose()

        MessageBox.Show( _
            "Đã xuất BOM thành công." & vbCrLf & vbCrLf & _
            "Số dòng: " & rowsToExport.Count.ToString() & vbCrLf & _
            "Đường dẫn:" & vbCrLf & saveDialog.FileName, _
            "BOM TOOL PRO", MessageBoxButtons.OK, MessageBoxIcon.Information)

    Catch ex As Exception
        Try
            progress.Close()
            progress.Dispose()
        Catch
        End Try
        MessageBox.Show("Không thể xuất Excel." & vbCrLf & ex.Message, "BOM TOOL PRO", MessageBoxButtons.OK, MessageBoxIcon.Error)
    End Try
End Sub

'====================================================================
' LÀM MỚI ĐÚNG CÁC DÒNG VÀ CỘT ĐÃ CHỌN
'====================================================================
Sub RefreshRowsFromViewer( _
    ByVal rowsToRefresh As List(Of PartBomItem), _
    ByVal selectedProperties As List(Of PropertyColumnInfo))

    If rowsToRefresh Is Nothing OrElse rowsToRefresh.Count = 0 Then Exit Sub

    Dim sw As Stopwatch = Stopwatch.StartNew()
    For Each item As PartBomItem In rowsToRefresh
        If item Is Nothing OrElse item.Document Is Nothing Then Continue For
        'Part thay đổi: invalidate geometry cache; Core refresh vẫn giữ nhẹ.
        BomGeometryEngine.Invalidate(item)
        CacheCorePartData(item)
        item.SelectedPropertyValues.Clear()
        ReadSelectedPropertiesForDocument(item, selectedProperties)
        BomSignatureEngine.CaptureIntoItem(item)
    Next
    BomLogger.Info("REFRESH_PROPERTIES", "Refreshed " & rowsToRefresh.Count.ToString() & " Part in " & sw.ElapsedMilliseconds.ToString() & " ms")
End Sub

'====================================================================
' KIỂM TRA YÊU CẦU HỦY
'====================================================================

'####################################################################
' SECTION 03 - SCAN CONTROL / CANCELLATION
' Kiểm soát hủy an toàn và trạng thái tiến trình.
'####################################################################

Sub CheckCancel(ByVal progressForm As BomProgressForm)
    WinFormsApplication.DoEvents()

    If progressForm IsNot Nothing AndAlso progressForm.CancelRequested Then
        Throw New OperationCanceledException()
    End If
End Sub

'====================================================================
' QUÉT ĐỆ QUY ASSEMBLY
'====================================================================

'####################################################################
' SECTION 04 - INVENTOR ASSEMBLY SCAN ENGINE
' Quét occurrence, bung cấu trúc, gộp Part và xây dữ liệu BOM.
'####################################################################

Sub ScanOccurrences( _
    ByVal occurrences As ComponentOccurrences, _
    ByVal immediateParentAssembly As String, _
    ByVal immediateParentPath As String, _
    ByVal partDictionary As Dictionary(Of String, PartBomItem), _
    ByVal progressForm As BomProgressForm, _
    ByRef scannedOccurrenceCount As Integer)

    If occurrences Is Nothing Then Exit Sub

    For Each occurrence As ComponentOccurrence In occurrences

        scannedOccurrenceCount += 1
        BomPerformanceCounters.OccurrenceTraversal += 1

        If scannedOccurrenceCount Mod 25 = 0 Then
            progressForm.SetStatus( _
                "Đang quét cấu trúc Assembly..." & vbCrLf & _
                "Đã kiểm tra: " & scannedOccurrenceCount.ToString() & " component" & vbCrLf & _
                "Đã tìm thấy: " & partDictionary.Count.ToString() & " loại Part")
            CheckCancel(progressForm)
        End If

        Try
            If occurrence.Suppressed Then Continue For

            Dim referencedDocument As Inventor.Document = Nothing

            Try
                referencedDocument = _
                    occurrence.ReferencedDocumentDescriptor.ReferencedDocument
            Catch
                Try
                    referencedDocument = occurrence.Definition.Document
                Catch
                    referencedDocument = Nothing
                End Try
            End Try

            If referencedDocument Is Nothing Then Continue For

            If referencedDocument.DocumentType = _
               DocumentTypeEnum.kPartDocumentObject Then

                AddPartToDictionary( _
                    referencedDocument, _
                    occurrence, _
                    immediateParentAssembly, _
                    immediateParentPath, _
                    partDictionary)

            ElseIf referencedDocument.DocumentType = _
                   DocumentTypeEnum.kAssemblyDocumentObject Then

                Dim subAssemblyName As String = _
                    GetDocumentPartNumberOrFileName(referencedDocument)

                Dim subOccurrences As ComponentOccurrences = Nothing

                Try
                    subOccurrences = occurrence.SubOccurrences
                Catch
                    subOccurrences = Nothing
                End Try

                If subOccurrences IsNot Nothing Then
                    Dim subAssemblyPath As String = immediateParentPath
                    If String.IsNullOrWhiteSpace(subAssemblyPath) Then
                        subAssemblyPath = subAssemblyName
                    Else
                        subAssemblyPath &= "\" & subAssemblyName
                    End If

                    ScanOccurrences( _
                        subOccurrences, _
                        subAssemblyName, _
                        subAssemblyPath, _
                        partDictionary, _
                        progressForm, _
                        scannedOccurrenceCount)
                End If
            End If

        Catch ex As Exception
            BomLogger.Add(BomLogLevel.Warning, "SCAN", "Bỏ qua occurrence lỗi: " & ex.Message)
        End Try
    Next

End Sub

'====================================================================
' THÊM/GỘP PART
'====================================================================
Sub AddPartToDictionary( _
    ByVal partDocument As Inventor.Document, _
    ByVal sourceOccurrence As ComponentOccurrence, _
    ByVal parentAssembly As String, _
    ByVal parentAssemblyPath As String, _
    ByVal partDictionary As Dictionary(Of String, PartBomItem))

    If partDocument Is Nothing Then Exit Sub

    Dim documentKey As String = ""

    Try
        documentKey = partDocument.FullFileName
    Catch
        documentKey = ""
    End Try

    If String.IsNullOrWhiteSpace(documentKey) Then
        Try
            documentKey = partDocument.InternalName
        Catch
            Try
                documentKey = partDocument.DisplayName
            Catch
                documentKey = Guid.NewGuid().ToString()
            End Try
        End Try
    End If

    documentKey = documentKey.Trim()
    If String.IsNullOrWhiteSpace(documentKey) Then Exit Sub

    Dim item As PartBomItem = Nothing

    If partDictionary.TryGetValue(documentKey, item) Then
        item.Quantity += 1
        item.AddParentAssembly(parentAssembly)
        item.AddAssemblyPath(parentAssemblyPath)
        item.AddOccurrence(sourceOccurrence)
    Else
        item = New PartBomItem()
        item.DocumentKey = documentKey
        item.Document = partDocument
        item.Quantity = 1
        item.FileName = GetSafeFileName(partDocument)
        item.FilePath = GetSafeFullFileName(partDocument)
        item.PartNumber = GetDocumentPartNumberOrFileName(partDocument)
        item.AddParentAssembly(parentAssembly)
        item.AddAssemblyPath(parentAssemblyPath)
        item.AddOccurrence(sourceOccurrence)
        CacheCorePartData(item)
        partDictionary.Add(documentKey, item)
    End If

End Sub

'====================================================================
' CHỈ QUÉT TÊN IPROPERTY
'====================================================================
Public Shared Sub ScanDocumentPropertyNames( _
    ByVal oDoc As Inventor.Document, _
    ByVal propertyDictionary As Dictionary(Of String, PropertyColumnInfo))

    If oDoc Is Nothing Then Exit Sub

    Dim propertySets As Inventor.PropertySets = Nothing

    Try
        propertySets = oDoc.PropertySets
    Catch
        Exit Sub
    End Try

    For Each propertySet As Inventor.PropertySet In propertySets

        Dim setDisplayName As String = ""
        Dim setInternalName As String = ""

        Try
            setDisplayName = propertySet.DisplayName
        Catch
        End Try

        Try
            setInternalName = propertySet.InternalName
        Catch
        End Try

        If ShouldSkipPropertySet(setDisplayName, setInternalName) Then
            Continue For
        End If

        For Each inventorProperty As Inventor.Property In propertySet
            Try
                Dim propertyName As String = inventorProperty.Name

                If String.IsNullOrWhiteSpace(propertyName) Then Continue For

                If String.Equals( _
                    propertyName, _
                    "Thumbnail", _
                    StringComparison.OrdinalIgnoreCase) Then
                    Continue For
                End If

                Dim propertyKey As String = _
                    BuildPropertyKey(setInternalName, propertyName)

                If Not propertyDictionary.ContainsKey(propertyKey) Then
                    Dim columnInfo As New PropertyColumnInfo()
                    columnInfo.Key = propertyKey
                    columnInfo.PropertySetDisplayName = setDisplayName
                    columnInfo.PropertySetInternalName = setInternalName
                    columnInfo.PropertyName = propertyName
                    columnInfo.DisplayText = _
                        BuildPropertyDisplayText(setDisplayName, propertyName)
                    columnInfo.DefaultSelected = IsDefaultProperty(propertyName)
                    propertyDictionary.Add(propertyKey, columnInfo)
                End If

                'Không đọc Value tại đây
            Catch ex As Exception
                BomLogger.Add(BomLogLevel.Warning, "PROPERTY_SCAN", ex.Message, Nothing, TryGetDocumentPath(oDoc))
            End Try
        Next
    Next

End Sub

Public Shared Function TryGetDocumentPath(ByVal doc As Inventor.Document) As String
    If doc Is Nothing Then Return ""
    Try
        Return doc.FullFileName
    Catch
        Try
            Return doc.DisplayName
        Catch
            Return ""
        End Try
    End Try
End Function

'====================================================================
' CHỈ ĐỌC GIÁ TRỊ PROPERTY ĐÃ CHỌN
'====================================================================


'====================================================================
' UNIVERSAL PART / SHEET METAL CONTROL
' Các cột synthetic dùng chung transaction engine với iProperty.
'====================================================================
Private Const SystemSettingSetInternalName As String = "__HIEU_SYSTEM_SETTING__"
Private Const SystemSettingSetDisplayName As String = "Inventor / Model Settings"

Private Shared Function MakeSystemSetting(ByVal settingId As String, ByVal caption As String) As PropertyColumnInfo
    Dim p As New PropertyColumnInfo()
    p.IsSystemSetting = True
    p.SettingId = settingId
    p.PropertySetInternalName = SystemSettingSetInternalName
    p.PropertySetDisplayName = SystemSettingSetDisplayName
    p.PropertyName = caption
    p.Key = SystemSettingSetInternalName & "||" & settingId
    p.DisplayText = "[MODEL] " & caption
    p.DefaultSelected = False
    Return p
End Function

Private Shared Sub AddUniversalSystemSettings(ByVal available As List(Of PropertyColumnInfo))
    If available Is Nothing Then Exit Sub
    available.Add(MakeSystemSetting("PART.MATERIAL", "Material"))
    available.Add(MakeSystemSetting("PART.APPEARANCE", "Appearance"))
    available.Add(MakeSystemSetting("SM.RULE", "Sheet Metal Rule"))
    available.Add(MakeSystemSetting("SM.USE_RULE_THICKNESS", "Use Thickness From Rule"))
    available.Add(MakeSystemSetting("SM.THICKNESS", "Sheet Metal Thickness"))
    available.Add(MakeSystemSetting("SM.USE_RULE_MATERIAL", "Use Material From Rule"))
    available.Add(MakeSystemSetting("SM.UNFOLD_RULE", "Unfold Rule"))
    available.Add(MakeSystemSetting("SM.USE_RULE_UNFOLD", "Use Unfold Rule From Sheet Metal Rule"))
End Sub

Private Shared Function IsSheetMetalDocument(ByVal doc As Inventor.Document) As Boolean
    Try
        If Not TypeOf doc Is Inventor.PartDocument Then Return False
        Return TypeOf CType(doc, Inventor.PartDocument).ComponentDefinition Is Inventor.SheetMetalComponentDefinition
    Catch
        Return False
    End Try
End Function

Private Shared Function ParseBomBoolean(ByVal value As String) As Boolean
    Dim s As String = If(value, "").Trim().ToUpperInvariant()
    If s = "1" OrElse s = "TRUE" OrElse s = "YES" OrElse s = "Y" OrElse s = "ON" OrElse s = "CÓ" OrElse s = "CO" OrElse s = "X" Then Return True
    If s = "0" OrElse s = "FALSE" OrElse s = "NO" OrElse s = "N" OrElse s = "OFF" OrElse s = "KHÔNG" OrElse s = "KHONG" OrElse s = "" Then Return False
    Throw New Exception("Giá trị Boolean không hợp lệ: '" & value & "'. Dùng TRUE/FALSE, YES/NO hoặc 1/0.")
End Function

Private Shared Function ReadSystemSettingValue(ByVal doc As Inventor.Document, ByVal info As PropertyColumnInfo) As Object
    If doc Is Nothing OrElse info Is Nothing Then Return ""
    Try
        Dim partDoc As Inventor.PartDocument = TryCast(doc, Inventor.PartDocument)
        Select Case info.SettingId
            Case "PART.MATERIAL"
                If partDoc Is Nothing OrElse partDoc.ActiveMaterial Is Nothing Then Return ""
                Return partDoc.ActiveMaterial.DisplayName
            Case "PART.APPEARANCE"
                If partDoc Is Nothing OrElse partDoc.ActiveAppearance Is Nothing Then Return ""
                Return partDoc.ActiveAppearance.DisplayName
        End Select

        If partDoc Is Nothing OrElse Not TypeOf partDoc.ComponentDefinition Is Inventor.SheetMetalComponentDefinition Then Return ""
        Dim sm As Inventor.SheetMetalComponentDefinition = CType(partDoc.ComponentDefinition, Inventor.SheetMetalComponentDefinition)

        Select Case info.SettingId
            Case "SM.RULE"
                If sm.ActiveSheetMetalStyle Is Nothing Then Return ""
                Return sm.ActiveSheetMetalStyle.Name
            Case "SM.USE_RULE_THICKNESS"
                Return sm.UseSheetMetalStyleThickness
            Case "SM.THICKNESS"
                If sm.Thickness Is Nothing Then Return ""
                Return sm.Thickness.Expression
            Case "SM.USE_RULE_MATERIAL"
                Return sm.UseSheetMetalStyleMaterial
            Case "SM.UNFOLD_RULE"
                If sm.UnfoldMethod Is Nothing Then Return ""
                Return sm.UnfoldMethod.Name
            Case "SM.USE_RULE_UNFOLD"
                Return sm.UseSheetMetalStyleUnfoldMethod
        End Select
    Catch ex As Exception
        BomLogger.Add(BomLogLevel.Warning, "SYSTEM_SETTING_READ", info.SettingId & ": " & ex.Message, Nothing, TryGetDocumentPath(doc))
    End Try
    Return ""
End Function

Private Shared Function FindMaterialAsset(ByVal partDoc As Inventor.PartDocument, ByVal requestedName As String) As Inventor.Asset
    If partDoc Is Nothing OrElse String.IsNullOrWhiteSpace(requestedName) Then Return Nothing
    Dim wanted As String = requestedName.Trim()

    Try
        For Each a As Inventor.Asset In partDoc.MaterialAssets
            If String.Equals(a.DisplayName, wanted, StringComparison.OrdinalIgnoreCase) OrElse
               String.Equals(a.Name, wanted, StringComparison.OrdinalIgnoreCase) Then Return a
        Next
    Catch
    End Try

    Try
        Dim invApp As Inventor.Application = CType(partDoc.Parent, Inventor.Application)
        For Each assetLibrary As Inventor.AssetLibrary In invApp.AssetLibraries
            Try
                For Each a As Inventor.Asset In assetLibrary.MaterialAssets
                    If String.Equals(a.DisplayName, wanted, StringComparison.OrdinalIgnoreCase) OrElse
                       String.Equals(a.Name, wanted, StringComparison.OrdinalIgnoreCase) Then
                        Dim localAsset As Inventor.Asset = a.CopyTo(partDoc)
                        Return localAsset
                    End If
                Next
            Catch
            End Try
        Next
    Catch
    End Try
    Return Nothing
End Function

Private Shared Function FindAppearanceAsset(ByVal partDoc As Inventor.PartDocument, ByVal requestedName As String) As Inventor.Asset
    If partDoc Is Nothing OrElse String.IsNullOrWhiteSpace(requestedName) Then Return Nothing
    Dim wanted As String = requestedName.Trim()

    Try
        For Each a As Inventor.Asset In partDoc.AppearanceAssets
            If String.Equals(a.DisplayName, wanted, StringComparison.OrdinalIgnoreCase) OrElse
               String.Equals(a.Name, wanted, StringComparison.OrdinalIgnoreCase) Then Return a
        Next
    Catch
    End Try

    Try
        Dim invApp As Inventor.Application = CType(partDoc.Parent, Inventor.Application)
        For Each assetLibrary As Inventor.AssetLibrary In invApp.AssetLibraries
            Try
                For Each a As Inventor.Asset In assetLibrary.AppearanceAssets
                    If String.Equals(a.DisplayName, wanted, StringComparison.OrdinalIgnoreCase) OrElse
                       String.Equals(a.Name, wanted, StringComparison.OrdinalIgnoreCase) Then
                        Dim localAsset As Inventor.Asset = a.CopyTo(partDoc)
                        Return localAsset
                    End If
                Next
            Catch
            End Try
        Next
    Catch
    End Try
    Return Nothing
End Function

Private Shared Sub WriteSystemSettingValue(ByVal doc As Inventor.Document, ByVal info As PropertyColumnInfo, ByVal newValue As String)
    If doc Is Nothing OrElse info Is Nothing Then Throw New Exception("System setting không hợp lệ.")
    Dim partDoc As Inventor.PartDocument = TryCast(doc, Inventor.PartDocument)

    Select Case info.SettingId
        Case "PART.MATERIAL"
            If partDoc Is Nothing Then Throw New Exception("Material chỉ áp dụng cho Part.")
            Dim mat As Inventor.Asset = FindMaterialAsset(partDoc, newValue)
            If mat Is Nothing Then Throw New Exception("Không tìm thấy Material: " & newValue)
            partDoc.ActiveMaterial = mat
            Exit Sub

        Case "PART.APPEARANCE"
            If partDoc Is Nothing Then Throw New Exception("Appearance chỉ áp dụng cho Part.")
            Dim app As Inventor.Asset = FindAppearanceAsset(partDoc, newValue)
            If app Is Nothing Then Throw New Exception("Không tìm thấy Appearance: " & newValue)
            partDoc.ActiveAppearance = app
            Exit Sub
    End Select

    If partDoc Is Nothing OrElse Not TypeOf partDoc.ComponentDefinition Is Inventor.SheetMetalComponentDefinition Then
        Throw New Exception("'" & info.PropertyName & "' chỉ áp dụng cho Sheet Metal Part.")
    End If

    Dim sm As Inventor.SheetMetalComponentDefinition = CType(partDoc.ComponentDefinition, Inventor.SheetMetalComponentDefinition)

    Select Case info.SettingId
        Case "SM.RULE"
            Dim target As Inventor.SheetMetalStyle = Nothing
            Try : target = sm.SheetMetalStyles.Item(newValue.Trim()) : Catch : End Try
            If target Is Nothing Then Throw New Exception("Không tìm thấy Sheet Metal Rule: " & newValue)
            target.Activate()

        Case "SM.USE_RULE_THICKNESS"
            sm.UseSheetMetalStyleThickness = ParseBomBoolean(newValue)

        Case "SM.THICKNESS"
            'Khi người dùng sửa Thickness trực tiếp, tự chuyển sang override để giá trị có hiệu lực.
            sm.UseSheetMetalStyleThickness = False
            sm.Thickness.Expression = newValue.Trim()

        Case "SM.USE_RULE_MATERIAL"
            sm.UseSheetMetalStyleMaterial = ParseBomBoolean(newValue)

        Case "SM.UNFOLD_RULE"
            Dim targetUnfold As Inventor.UnfoldMethod = Nothing
            Try : targetUnfold = sm.UnfoldMethods.Item(newValue.Trim()) : Catch : End Try
            If targetUnfold Is Nothing Then Throw New Exception("Không tìm thấy Unfold Rule: " & newValue)
            sm.UseSheetMetalStyleUnfoldMethod = False
            sm.UnfoldMethod = targetUnfold

        Case "SM.USE_RULE_UNFOLD"
            sm.UseSheetMetalStyleUnfoldMethod = ParseBomBoolean(newValue)

        Case Else
            Throw New Exception("Chưa có handler cho setting: " & info.SettingId)
    End Select
End Sub


'####################################################################
' SECTION 05 - IPROPERTY READ ENGINE
' Đọc đúng các iProperty được chọn và giảm COM Call.
'####################################################################

Sub ReadSelectedPropertiesOnly( _
    ByVal bomItems As List(Of PartBomItem), _
    ByVal selectedProperties As List(Of PropertyColumnInfo), _
    ByVal progressForm As BomProgressForm)

    Dim totalParts As Integer = bomItems.Count
    Dim currentPart As Integer = 0
    Dim sw As Stopwatch = Stopwatch.StartNew()

    For Each item As PartBomItem In bomItems
        CheckCancel(progressForm)
        currentPart += 1
        item.SelectedPropertyValues.Clear()

        If item.Document IsNot Nothing Then
            ReadSelectedPropertiesForDocument(item, selectedProperties)
        End If

        If currentPart Mod 10 = 0 OrElse currentPart = totalParts Then
            Dim percent As Integer = 55
            If totalParts > 0 Then
                percent = 55 + CInt((CDbl(currentPart) / CDbl(totalParts)) * 19)
            End If
            progressForm.SetProgress( _
                Math.Min(percent, 74), _
                "Đang đọc thông tin đã chọn..." & vbCrLf & _
                currentPart.ToString() & " / " & totalParts.ToString() & " Part" & vbCrLf & _
                "Số cột đã chọn: " & selectedProperties.Count.ToString())
        End If
    Next

    BomLogger.Info("PROPERTY_READ", "Read " & totalParts.ToString() & " Part x " & selectedProperties.Count.ToString() & " columns in " & sw.ElapsedMilliseconds.ToString() & " ms")
End Sub

Sub ReadSelectedPropertiesForDocument(ByVal item As PartBomItem, ByVal selectedProperties As List(Of PropertyColumnInfo))
    If item Is Nothing OrElse item.Document Is Nothing OrElse selectedProperties Is Nothing Then Exit Sub

    Dim localWatch As Stopwatch = Stopwatch.StartNew()
    BomPerformanceCounters.DocumentAccess += 1
    Dim setCache As New Dictionary(Of String, Inventor.PropertySet)(StringComparer.OrdinalIgnoreCase)
    Try
        For Each info As PropertyColumnInfo In selectedProperties
            BomPerformanceCounters.PropertyRead += 1
            Dim value As Object = ""
            If info IsNot Nothing AndAlso info.IsSystemSetting Then
                value = ReadSystemSettingValue(item.Document, info)
                item.SelectedPropertyValues(info.Key) = value
                Continue For
            End If
            Try
                Dim setObj As Inventor.PropertySet = Nothing
                If Not setCache.TryGetValue(info.PropertySetInternalName, setObj) Then
                    setObj = item.Document.PropertySets.Item(info.PropertySetInternalName)
                    setCache(info.PropertySetInternalName) = setObj
                End If
                Dim prop As Inventor.Property = setObj.Item(info.PropertyName)
                If prop IsNot Nothing AndAlso prop.Value IsNot Nothing Then value = prop.Value
            Catch ex As Exception
                BomLogger.Warn("PROPERTY_READ", info.PropertyName & ": " & ex.Message, item)
                value = ""
            End Try
            item.SelectedPropertyValues(info.Key) = value
        Next
    Finally
        setCache.Clear()
        localWatch.Stop()
        BomPerformanceCounters.PropertyReadMs += localWatch.ElapsedMilliseconds
    End Try
End Sub

'====================================================================
' ĐỌC MỘT PROPERTY ĐÃ CHỌN
'====================================================================
Public Shared Function ReadSingleSelectedProperty( _
    ByVal oDoc As Inventor.Document, _
    ByVal propertyInfo As PropertyColumnInfo) As Object

    If oDoc Is Nothing OrElse propertyInfo Is Nothing Then Return ""
    If propertyInfo.IsSystemSetting Then Return ReadSystemSettingValue(oDoc, propertyInfo)

    Try
        Dim propertySet As Inventor.PropertySet = Nothing

        Try
            propertySet = oDoc.PropertySets.Item( _
                propertyInfo.PropertySetInternalName)
        Catch
            Return ""
        End Try

        Dim inventorProperty As Inventor.Property = Nothing

        Try
            inventorProperty = propertySet.Item(propertyInfo.PropertyName)
        Catch
            Return ""
        End Try

        Return ConvertPropertyValue(inventorProperty.Value)
    Catch
        Return ""
    End Try

End Function

'====================================================================
' XUẤT EXCEL
'====================================================================

'####################################################################
' SECTION 06 - EXCEL EXPORT ENGINE
' Xuất BOM, cấu trúc Assembly, Summary và định dạng Excel.
'####################################################################

Sub ExportBomToExcel( _
    ByVal assemblyDocument As AssemblyDocument, _
    ByVal bomItems As List(Of PartBomItem), _
    ByVal selectedProperties As List(Of PropertyColumnInfo), _
    ByVal includeFileName As Boolean, _
    ByVal includeFilePath As Boolean, _
    ByVal includeParentAssembly As Boolean, _
    ByVal outputPath As String, _
    ByVal openExcelAfterExport As Boolean, _
    ByVal progressForm As BomProgressForm)

    Dim excelApplication As Object = Nothing
    Dim workbook As Object = Nothing
    Dim worksheet As Object = Nothing
    Dim tableRange As Object = Nothing
    Dim listObject As Object = Nothing
    Dim excelWasVisible As Boolean = False

    Try
        CheckCancel(progressForm)

        progressForm.SetProgress(78, "Đang khởi động Microsoft Excel...")

        Try
            excelApplication = CreateObject("Excel.Application")
        Catch
            Throw New Exception( _
                "Không khởi động được Microsoft Excel." & vbCrLf & _
                "Hãy kiểm tra Excel đã được cài trên máy.")
        End Try

        excelApplication.DisplayAlerts = False
        excelApplication.ScreenUpdating = False
        excelApplication.EnableEvents = False
        excelApplication.Visible = False

        workbook = excelApplication.Workbooks.Add()
        worksheet = workbook.Worksheets(1)
        worksheet.Name = "THEO PART"
        'Bảo đảm Workbook chỉ còn Sheet THEO PART trước khi tạo Sheet THEO ASSEMBLY.
        While workbook.Worksheets.Count > 1
            workbook.Worksheets(workbook.Worksheets.Count).Delete()
        End While

        progressForm.SetProgress(82, "Đang tạo cấu trúc bảng Excel...")
        CheckCancel(progressForm)

        Dim totalColumns As Integer = 6
        If includeFileName Then totalColumns += 1
        If includeFilePath Then totalColumns += 1
        If includeParentAssembly Then totalColumns += 1
        totalColumns += selectedProperties.Count

        Dim titleRow As Integer = 1
        Dim infoRow As Integer = 2
        Dim headerRow As Integer = 4
        Dim firstDataRow As Integer = 5
        Dim lastDataRow As Integer = firstDataRow + bomItems.Count - 1
        Dim lastColumnLetter As String = ExcelColumnLetter(totalColumns)

        Dim titleRange As Object = worksheet.Range( _
            "A" & titleRow.ToString(), _
            lastColumnLetter & titleRow.ToString())

        titleRange.Merge()
        titleRange.Value = "BOM THEO PART"
        titleRange.Font.Bold = True
        titleRange.Font.Size = 16
        titleRange.HorizontalAlignment = -4108
        titleRange.VerticalAlignment = -4108
        titleRange.RowHeight = 28

        Dim infoRange As Object = worksheet.Range( _
            "A" & infoRow.ToString(), _
            lastColumnLetter & infoRow.ToString())

        infoRange.Merge()
        infoRange.Value = _
            "Assembly: " & GetDocumentPartNumberOrFileName(assemblyDocument) & _
            "    |    Exported: " & DateTime.Now.ToString("dd/MM/yyyy HH:mm") & _
            "    |    Unique parts: " & bomItems.Count.ToString()

        infoRange.Font.Size = 10
        infoRange.Font.Italic = True
        infoRange.HorizontalAlignment = -4108
        infoRange.VerticalAlignment = -4108
        infoRange.RowHeight = 20

        '==============================================================
        ' TẠO MẢNG DATA .NET - KHÔNG GỌI LẠI INVENTOR API
        '==============================================================
        Dim dataRowCount As Integer = bomItems.Count + 1
        Dim dataArray(dataRowCount - 1, totalColumns - 1) As Object
        Dim currentColumn As Integer = 0

        dataArray(0, currentColumn) = "ITEM"
        currentColumn += 1

        dataArray(0, currentColumn) = "QTY"
        currentColumn += 1
        dataArray(0, currentColumn) = "DẠNG CHI TIẾT"
        currentColumn += 1
        dataArray(0, currentColumn) = "THICK (" & BomUnitManager.LengthUnit & ")"
        currentColumn += 1
        dataArray(0, currentColumn) = "NGUỒN THICK"
        currentColumn += 1
        dataArray(0, currentColumn) = "BOUNDING BOX L x W x H (" & BomUnitManager.LengthUnit & ")"
        currentColumn += 1

        If includeFileName Then
            dataArray(0, currentColumn) = "FILE NAME"
            currentColumn += 1
        End If

        If includeFilePath Then
            dataArray(0, currentColumn) = "FILE PATH"
            currentColumn += 1
        End If

        If includeParentAssembly Then
            dataArray(0, currentColumn) = "NẰM TRONG ASSEMBLY"
            currentColumn += 1
        End If

        For Each propertyInfo As PropertyColumnInfo In selectedProperties
            dataArray(0, currentColumn) = _
                BomUnitManager.GetPropertyHeader(propertyInfo.PropertyName)
            currentColumn += 1
        Next

        progressForm.SetProgress(86, "Đang tạo dữ liệu BOM trong bộ nhớ...")

        For rowIndex As Integer = 0 To bomItems.Count - 1
            CheckCancel(progressForm)

            Dim item As PartBomItem = bomItems(rowIndex)
            'Export profile hiện có chứa Geometry/Thickness/BoundingBox => load đúng lúc export cần.
            BomGeometryEngine.EnsureLoaded(item)
            currentColumn = 0

            dataArray(rowIndex + 1, currentColumn) = rowIndex + 1
            currentColumn += 1

            dataArray(rowIndex + 1, currentColumn) = item.Quantity
            currentColumn += 1
            dataArray(rowIndex + 1, currentColumn) = item.GeometryType
            currentColumn += 1
            dataArray(rowIndex + 1, currentColumn) = BomUnitManager.ConvertLengthFromMm(item.Thickness)
            currentColumn += 1
            dataArray(rowIndex + 1, currentColumn) = item.ThicknessSource
            currentColumn += 1
            dataArray(rowIndex + 1, currentColumn) = BomUnitManager.FormatBoundingBox(item)
            currentColumn += 1

            If includeFileName Then
                dataArray(rowIndex + 1, currentColumn) = item.FileName
                currentColumn += 1
            End If

            If includeFilePath Then
                dataArray(rowIndex + 1, currentColumn) = item.FilePath
                currentColumn += 1
            End If

            If includeParentAssembly Then
                dataArray(rowIndex + 1, currentColumn) = item.GetParentAssemblyText()
                currentColumn += 1
            End If

            For Each propertyInfo As PropertyColumnInfo In selectedProperties
                Dim valueToExport As Object = ""

                valueToExport = BomUnitManager.GetPropertyDisplayValue(item, propertyInfo)

                dataArray(rowIndex + 1, currentColumn) = valueToExport
                currentColumn += 1
            Next

            If rowIndex Mod 100 = 0 Then
                progressForm.SetStatus( _
                    "Đang tạo dữ liệu BOM trong bộ nhớ..." & vbCrLf & _
                    (rowIndex + 1).ToString() & " / " & bomItems.Count.ToString() & " dòng")
            End If
        Next

        progressForm.SetProgress(90, "Đang ghi toàn bộ dữ liệu vào Excel...")
        CheckCancel(progressForm)

        tableRange = worksheet.Range( _
            "A" & headerRow.ToString(), _
            lastColumnLetter & lastDataRow.ToString())

        'QUAN TRỌNG:
        'Định dạng toàn bộ vùng thành Text TRƯỚC KHI ghi dữ liệu.
        'Nhờ vậy các mã như 7-140, 22-7, 29-7... không bị Excel
        'tự động chuyển thành ngày tháng.
        tableRange.NumberFormat = "@"

        tableRange.Value2 = dataArray

        'Giữ nguyên tất cả các cột ở dạng Text.
        'Không chuyển riêng ITEM, QTY hoặc bất kỳ cột nào sang Number/Date.

        progressForm.SetProgress(93, "Đang định dạng bảng Excel...")

        worksheet.Cells.Font.Name = "Arial"
        worksheet.Cells.Font.Size = 10
        worksheet.Cells.VerticalAlignment = -4108

        Dim headerRange As Object = worksheet.Range( _
            "A" & headerRow.ToString(), _
            lastColumnLetter & headerRow.ToString())

        headerRange.Font.Bold = True
        headerRange.Font.Size = 10
        headerRange.HorizontalAlignment = -4108
        headerRange.VerticalAlignment = -4108
        headerRange.WrapText = True
        headerRange.RowHeight = 30
        headerRange.Interior.Color = RGBValue(31, 78, 121)
        headerRange.Font.Color = RGBValue(255, 255, 255)

        tableRange.Borders.LineStyle = 1
        tableRange.Borders.Weight = 2

        'FAST MODE: AutoFilter nhanh hơn ListObject/Table Style đáng kể.
        Try
            headerRange.AutoFilter()
        Catch
        End Try

        worksheet.Columns(1).HorizontalAlignment = -4108
        worksheet.Columns(2).HorizontalAlignment = -4108
        worksheet.Columns(1).ColumnWidth = 8
        worksheet.Columns(2).ColumnWidth = 8
        worksheet.Columns(3).ColumnWidth = 18
        worksheet.Columns(4).ColumnWidth = 12
        worksheet.Columns(5).ColumnWidth = 16
        worksheet.Columns(6).ColumnWidth = 30

        Dim excelColumnIndex As Integer = 7

        If includeFileName Then
            worksheet.Columns(excelColumnIndex).HorizontalAlignment = -4131
            worksheet.Columns(excelColumnIndex).ColumnWidth = 28
            excelColumnIndex += 1
        End If

        If includeFilePath Then
            worksheet.Columns(excelColumnIndex).HorizontalAlignment = -4131
            worksheet.Columns(excelColumnIndex).ColumnWidth = 55
            excelColumnIndex += 1
        End If

        If includeParentAssembly Then
            worksheet.Columns(excelColumnIndex).HorizontalAlignment = -4131
            worksheet.Columns(excelColumnIndex).ColumnWidth = 32
            worksheet.Columns(excelColumnIndex).WrapText = True
            excelColumnIndex += 1
        End If

        For Each propertyInfo As PropertyColumnInfo In selectedProperties
            Dim propertyColumn As Object = worksheet.Columns(excelColumnIndex)
            propertyColumn.HorizontalAlignment = _
                GetPropertyHorizontalAlignment(propertyInfo.PropertyName)
            propertyColumn.ColumnWidth = _
                GetRecommendedColumnWidth(propertyInfo.PropertyName)
            propertyColumn.WrapText = _
                ShouldWrapProperty(propertyInfo.PropertyName)
            excelColumnIndex += 1
        Next

        For columnIndex As Integer = 1 To totalColumns
            Dim currentWidth As Double = 15

            Try
                currentWidth = CDbl(worksheet.Columns(columnIndex).ColumnWidth)
            Catch
            End Try

            If currentWidth < 8 Then
                worksheet.Columns(columnIndex).ColumnWidth = 8
            ElseIf currentWidth > 55 Then
                worksheet.Columns(columnIndex).ColumnWidth = 55
            End If
        Next

        Dim dataRange As Object = worksheet.Range( _
            "A" & firstDataRow.ToString(), _
            lastColumnLetter & lastDataRow.ToString())

        dataRange.VerticalAlignment = -4108

        'Không AutoFit/lặp từng dòng qua COM. Đặt chiều cao cả vùng một lần.
        Try
            dataRange.RowHeight = 20
        Catch
        End Try

        worksheet.Activate()
        excelApplication.ActiveWindow.SplitColumn = 0
        excelApplication.ActiveWindow.SplitRow = 4
        excelApplication.ActiveWindow.FreezePanes = True

        'Bỏ PageSetup/Select trong chế độ nhanh để giảm COM call.
        WriteAssemblyHierarchySheet(workbook, bomItems, selectedProperties, includeFileName, includeFilePath)

        progressForm.SetProgress(97, _
            "Đang lưu file Excel..." & vbCrLf & outputPath)
        CheckCancel(progressForm)

        workbook.SaveAs(outputPath, 51)

        If openExcelAfterExport Then
            excelApplication.ScreenUpdating = True
            excelApplication.EnableEvents = True
            excelApplication.DisplayAlerts = True
            excelApplication.Visible = True
            excelWasVisible = True
        Else
            workbook.Close(False)
            excelApplication.Quit()
        End If

    Catch
        If workbook IsNot Nothing Then
            Try
                workbook.Close(False)
            Catch
            End Try
        End If

        If excelApplication IsNot Nothing Then
            Try
                excelApplication.Quit()
            Catch
            End Try
        End If

        Throw

    Finally
        ReleaseComObject(listObject)
        ReleaseComObject(tableRange)
        ReleaseComObject(worksheet)
        ReleaseComObject(workbook)
        ReleaseComObject(excelApplication)

        'Không cưỡng bức GC nhiều lần vì làm UI khựng.
        GC.Collect(0)
    End Try

End Sub

Sub WriteAssemblyHierarchySheet( _
    ByVal workbook As Object, _
    ByVal bomItems As List(Of PartBomItem), _
    ByVal selectedProperties As List(Of PropertyColumnInfo), _
    ByVal includeFileName As Boolean, _
    ByVal includeFilePath As Boolean)

    Dim sheet As Object = Nothing
    Dim usedRange As Object = Nothing

    Try
        sheet = workbook.Worksheets.Add(Nothing, workbook.Worksheets(workbook.Worksheets.Count))
        sheet.Name = "THEO ASSEMBLY"

        'Dựng cây từ đường dẫn đã Cache trong lần quét Inventor đầu tiên.
        'Không gọi lại Inventor API khi xuất Excel.
        Dim root As New AssemblyExportNode("", "")
        For Each item As PartBomItem In bomItems
            If item Is Nothing Then Continue For
            Dim paths As List(Of String) = item.GetAssemblyPaths()
            If paths.Count = 0 Then
                Dim fallbackParents As List(Of String) = item.GetParentAssemblies()
                For Each parentName As String In fallbackParents
                    If Not String.IsNullOrWhiteSpace(parentName) Then
                        root.AddPartByPath(parentName, item, item.GetQuantityForParent(parentName))
                    End If
                Next
            Else
                For Each assemblyPath As String In paths
                    root.AddPartByPath(assemblyPath, item, item.GetQuantityForAssemblyPath(assemblyPath))
                Next
            End If
        Next

        Dim totalColumns As Integer = 8 + selectedProperties.Count
        If includeFileName Then totalColumns += 1
        If includeFilePath Then totalColumns += 1
        Dim lastColumnLetter As String = ExcelColumnLetter(totalColumns)

        Dim rows As New List(Of Object())()
        Dim rowTypes As New List(Of Integer)() '0 title/info, 1 assembly, 2 header, 3 part
        Dim rowLevels As New List(Of Integer)()

        Dim title(totalColumns - 1) As Object
        title(0) = "BOM THEO ASSEMBLY - CẤU TRÚC MẸ / CON"
        rows.Add(title) : rowTypes.Add(0) : rowLevels.Add(0)

        Dim info(totalColumns - 1) As Object
        info(0) = "Assembly nguồn: " & GetDocumentPartNumberOrFileName(CType(ThisApplication.ActiveDocument, Inventor.Document)) & " | Xuất: " & DateTime.Now.ToString("dd/MM/yyyy HH:mm")
        rows.Add(info) : rowTypes.Add(0) : rowLevels.Add(0)

        Dim blank(totalColumns - 1) As Object
        rows.Add(blank) : rowTypes.Add(0) : rowLevels.Add(0)

        Dim roots As List(Of AssemblyExportNode) = root.GetSortedChildren()
        For Each rootNode As AssemblyExportNode In roots
            AppendAssemblyExportRows(rootNode, 0, rows, rowTypes, rowLevels, totalColumns, selectedProperties, includeFileName, includeFilePath)
        Next

        If rows.Count = 3 Then
            Dim emptyRow(totalColumns - 1) As Object
            emptyRow(0) = "Không có dữ liệu Assembly để xuất."
            rows.Add(emptyRow) : rowTypes.Add(0) : rowLevels.Add(0)
        End If

        Dim values(rows.Count - 1, totalColumns - 1) As Object
        For rowIndex As Integer = 0 To rows.Count - 1
            Dim sourceRow() As Object = rows(rowIndex)
            For colIndex As Integer = 0 To totalColumns - 1
                values(rowIndex, colIndex) = sourceRow(colIndex)
            Next
        Next

        usedRange = sheet.Range("A1", lastColumnLetter & rows.Count.ToString())
        usedRange.NumberFormat = "@"
        usedRange.Value2 = values

        sheet.Cells.Font.Name = "Arial"
        sheet.Cells.Font.Size = 10
        sheet.Cells.VerticalAlignment = -4108
        sheet.Columns(1).ColumnWidth = 8
        sheet.Columns(2).ColumnWidth = 10
        sheet.Columns(3).ColumnWidth = 14
        sheet.Columns(4).ColumnWidth = 24
        sheet.Columns(5).ColumnWidth = 34
        sheet.Columns(6).ColumnWidth = 22
        sheet.Columns(7).ColumnWidth = 12
        sheet.Columns(8).ColumnWidth = 28

        sheet.Range("A1", lastColumnLetter & "1").Merge()
        sheet.Range("A1").Font.Bold = True
        sheet.Range("A1").Font.Size = 16
        sheet.Range("A1").HorizontalAlignment = -4108
        sheet.Range("A2", lastColumnLetter & "2").Merge()
        sheet.Range("A2").Font.Italic = True

        'Định dạng theo metadata đã dựng trong RAM; không lặp quét Part theo Assembly.
        For i As Integer = 3 To rows.Count - 1
            Dim excelRow As Integer = i + 1
            Select Case rowTypes(i)
                Case 1 'Assembly
                    With sheet.Range("A" & excelRow.ToString(), lastColumnLetter & excelRow.ToString())
                        .Font.Bold = True
                        .Interior.Color = RGBValue(65, 120, 145)
                        .Font.Color = RGBValue(255, 255, 255)
                    End With
                    Try
                        sheet.Rows(excelRow).OutlineLevel = Math.Min(8, rowLevels(i) + 1)
                    Catch
                    End Try
                Case 2 'Header
                    With sheet.Range("A" & excelRow.ToString(), lastColumnLetter & excelRow.ToString())
                        .Font.Bold = True
                        .Interior.Color = RGBValue(210, 230, 238)
                    End With
                    Try
                        sheet.Rows(excelRow).OutlineLevel = Math.Min(8, rowLevels(i) + 1)
                    Catch
                    End Try
                Case 3 'Part
                    Try
                        sheet.Rows(excelRow).OutlineLevel = Math.Min(8, rowLevels(i) + 1)
                    Catch
                    End Try
            End Select
        Next

        usedRange.Borders.LineStyle = 1
        usedRange.Borders.Weight = 2
        sheet.Outline.SummaryRow = 0
        sheet.Activate()
        workbook.Application.ActiveWindow.SplitRow = 3
        workbook.Application.ActiveWindow.FreezePanes = True

    Catch
        'Không làm hỏng sheet THEO PART nếu sheet Assembly gặp lỗi định dạng.
    Finally
        ReleaseComObject(usedRange)
        ReleaseComObject(sheet)
    End Try
End Sub

Sub AppendAssemblyExportRows( _
    ByVal node As AssemblyExportNode, _
    ByVal level As Integer, _
    ByVal rows As List(Of Object()), _
    ByVal rowTypes As List(Of Integer), _
    ByVal rowLevels As List(Of Integer), _
    ByVal totalColumns As Integer, _
    ByVal selectedProperties As List(Of PropertyColumnInfo), _
    ByVal includeFileName As Boolean, _
    ByVal includeFilePath As Boolean)

    If node Is Nothing Then Exit Sub

    Dim assemblyRow(totalColumns - 1) As Object
    assemblyRow(0) = New String(" "c, level * 4) & "▼ ASSEMBLY: " & node.Name
    assemblyRow(1) = "LEVEL " & level.ToString()
    assemblyRow(2) = "PART TYPES: " & node.GetRecursiveUniquePartCount().ToString()
    assemblyRow(3) = "TOTAL QTY: " & node.GetRecursiveQuantity().ToString()
    assemblyRow(4) = "PATH: " & node.FullPath
    rows.Add(assemblyRow) : rowTypes.Add(1) : rowLevels.Add(level)

    If node.DirectParts.Count > 0 Then
        Dim header(totalColumns - 1) As Object
        Dim c As Integer = 0
        header(c) = "LEVEL" : c += 1
        header(c) = "ITEM" : c += 1
        header(c) = "QTY" : c += 1
        header(c) = "PART NUMBER" : c += 1
        header(c) = "DESCRIPTION" : c += 1
        header(c) = "MATERIAL" : c += 1
        header(c) = "THICK (" & BomUnitManager.LengthUnit & ")" : c += 1
        header(c) = "BOUNDING BOX (" & BomUnitManager.LengthUnit & ")" : c += 1
        If includeFileName Then header(c) = "FILE NAME" : c += 1
        If includeFilePath Then header(c) = "FILE PATH" : c += 1
        For Each pi As PropertyColumnInfo In selectedProperties
            header(c) = BomUnitManager.GetPropertyHeader(pi.PropertyName) : c += 1
        Next
        rows.Add(header) : rowTypes.Add(2) : rowLevels.Add(level + 1)

        Dim sortedParts As List(Of AssemblyExportPart) = node.GetSortedDirectParts()
        Dim itemNo As Integer = 1
        For Each partEntry As AssemblyExportPart In sortedParts
            Dim item As PartBomItem = partEntry.Item
            Dim partRow(totalColumns - 1) As Object
            c = 0
            partRow(c) = level + 1 : c += 1
            partRow(c) = itemNo : c += 1
            partRow(c) = partEntry.Quantity : c += 1
            partRow(c) = item.PartNumber : c += 1
            partRow(c) = item.Description : c += 1
            partRow(c) = item.Material : c += 1
            partRow(c) = BomUnitManager.ConvertLengthFromMm(item.Thickness) : c += 1
            partRow(c) = BomUnitManager.FormatBoundingBox(item) : c += 1
            If includeFileName Then partRow(c) = item.FileName : c += 1
            If includeFilePath Then partRow(c) = item.FilePath : c += 1
            For Each pi As PropertyColumnInfo In selectedProperties
                partRow(c) = BomUnitManager.GetPropertyDisplayValue(item, pi) : c += 1
            Next
            rows.Add(partRow) : rowTypes.Add(3) : rowLevels.Add(level + 1)
            itemNo += 1
        Next
    End If

    For Each child As AssemblyExportNode In node.GetSortedChildren()
        AppendAssemblyExportRows(child, level + 1, rows, rowTypes, rowLevels, totalColumns, selectedProperties, includeFileName, includeFilePath)
    Next
End Sub


'####################################################################
' SECTION 07 - ASSEMBLY EXPORT DATA MODELS
' Mô hình cây Assembly và Part dùng riêng cho xuất Excel cha-con.
'####################################################################

Public Class AssemblyExportPart
    Public Item As PartBomItem
    Public Quantity As Integer
End Class

Public Class AssemblyExportNode
    Public Name As String
    Public FullPath As String
    Public Children As New Dictionary(Of String, AssemblyExportNode)(StringComparer.OrdinalIgnoreCase)
    Public DirectParts As New Dictionary(Of String, AssemblyExportPart)(StringComparer.OrdinalIgnoreCase)

    Public Sub New(ByVal nodeName As String, ByVal nodePath As String)
        Name = If(nodeName, "")
        FullPath = If(nodePath, "")
    End Sub

    Public Sub AddPartByPath(ByVal assemblyPath As String, ByVal item As PartBomItem, ByVal quantity As Integer)
        If item Is Nothing OrElse String.IsNullOrWhiteSpace(assemblyPath) Then Exit Sub
        Dim parts() As String = assemblyPath.Trim().Trim("\"c).Split("\"c)
        Dim current As AssemblyExportNode = Me
        Dim pathBuilder As String = ""
        For Each rawName As String In parts
            Dim cleanName As String = rawName.Trim()
            If cleanName.Length = 0 Then Continue For
            If pathBuilder.Length = 0 Then pathBuilder = cleanName Else pathBuilder &= "\" & cleanName
            Dim child As AssemblyExportNode = Nothing
            If Not current.Children.TryGetValue(cleanName, child) Then
                child = New AssemblyExportNode(cleanName, pathBuilder)
                current.Children.Add(cleanName, child)
            End If
            current = child
        Next
        current.AddDirectPart(item, quantity)
    End Sub

    Private Sub AddDirectPart(ByVal item As PartBomItem, ByVal quantity As Integer)
        Dim key As String = item.DocumentKey
        If String.IsNullOrWhiteSpace(key) Then key = item.PartNumber & "|" & item.FileName
        Dim entry As AssemblyExportPart = Nothing
        If DirectParts.TryGetValue(key, entry) Then
            entry.Quantity += Math.Max(0, quantity)
        Else
            entry = New AssemblyExportPart()
            entry.Item = item
            entry.Quantity = Math.Max(0, quantity)
            DirectParts.Add(key, entry)
        End If
    End Sub

    Public Function GetSortedChildren() As List(Of AssemblyExportNode)
        Dim result As New List(Of AssemblyExportNode)(Children.Values)
        result.Sort(Function(a As AssemblyExportNode, b As AssemblyExportNode) StringComparer.OrdinalIgnoreCase.Compare(a.Name, b.Name))
        Return result
    End Function

    Public Function GetSortedDirectParts() As List(Of AssemblyExportPart)
        Dim result As New List(Of AssemblyExportPart)(DirectParts.Values)
        result.Sort(Function(a As AssemblyExportPart, b As AssemblyExportPart) StringComparer.OrdinalIgnoreCase.Compare(a.Item.PartNumber, b.Item.PartNumber))
        Return result
    End Function

    Public Function GetRecursiveQuantity() As Integer
        Dim total As Integer = 0
        For Each entry As AssemblyExportPart In DirectParts.Values
            total += Math.Max(0, entry.Quantity)
        Next
        For Each child As AssemblyExportNode In Children.Values
            total += child.GetRecursiveQuantity()
        Next
        Return total
    End Function

    Public Function GetRecursiveUniquePartCount() As Integer
        Dim keys As New HashSet(Of String)(StringComparer.OrdinalIgnoreCase)
        CollectPartKeys(keys)
        Return keys.Count
    End Function

    Private Sub CollectPartKeys(ByVal keys As HashSet(Of String))
        For Each key As String In DirectParts.Keys
            keys.Add(key)
        Next
        For Each child As AssemblyExportNode In Children.Values
            child.CollectPartKeys(keys)
        Next
    End Sub
End Class

'====================================================================
' HỖ TRỢ PROPERTY
'====================================================================
Public Shared Function ConvertPropertyValue(ByVal rawValue As Object) As Object
    If rawValue Is Nothing Then Return ""

    Try
        If TypeOf rawValue Is DateTime Then
            Return CType(rawValue, DateTime).ToString("dd/MM/yyyy")
        ElseIf TypeOf rawValue Is Boolean Then
            If CBool(rawValue) Then Return "Yes" Else Return "No"
        ElseIf TypeOf rawValue Is Byte() Then
            Return ""
        ElseIf Marshal.IsComObject(rawValue) Then
            Return ""
        Else
            Return Convert.ToString(rawValue)
        End If
    Catch
        Return ""
    End Try
End Function

Public Shared Function GetDocumentPartNumberOrFileName( _
    ByVal oDoc As Inventor.Document) As String

    If oDoc Is Nothing Then Return ""

    Dim partNumber As String = ""

    Try
        Dim designTrackingSet As PropertySet = _
            oDoc.PropertySets.Item( _
                "{32853F0F-3444-11D1-9E93-0060B03C1CA6}")

        Dim partNumberProperty As Inventor.Property = _
            designTrackingSet.Item("Part Number")

        partNumber = Convert.ToString(partNumberProperty.Value).Trim()
    Catch
        partNumber = ""
    End Try

    If Not String.IsNullOrWhiteSpace(partNumber) Then Return partNumber

    Dim safeName As String = GetSafeFileName(oDoc)

    Try
        Return IOPath.GetFileNameWithoutExtension(safeName)
    Catch
        Return safeName
    End Try
End Function

Public Shared Function GetSafeFileName(ByVal oDoc As Inventor.Document) As String
    If oDoc Is Nothing Then Return ""

    Try
        If Not String.IsNullOrWhiteSpace(oDoc.FullFileName) Then
            Return IOPath.GetFileName(oDoc.FullFileName)
        End If
    Catch
    End Try

    Try
        Return oDoc.DisplayName
    Catch
        Return ""
    End Try
End Function


'####################################################################
' SECTION 08 - COMMON UTILITIES / FORMAT / COM RELEASE
' Hàm dùng chung: đường dẫn, căn lề, màu, định dạng và giải phóng COM.
'####################################################################

Function GetSafeFullFileName(ByVal oDoc As Inventor.Document) As String
    If oDoc Is Nothing Then Return ""

    Try
        Return oDoc.FullFileName
    Catch
        Return ""
    End Try
End Function

Public Shared Function BuildPropertyKey( _
    ByVal setInternalName As String, _
    ByVal propertyName As String) As String

    Return If(setInternalName, "").Trim() & "||" & _
           If(propertyName, "").Trim()
End Function

Public Shared Function BuildPropertyDisplayText( _
    ByVal setDisplayName As String, _
    ByVal propertyName As String) As String

    If String.IsNullOrWhiteSpace(setDisplayName) Then Return propertyName
    Return propertyName & "    [" & setDisplayName & "]"
End Function

Public Shared Function ShouldSkipPropertySet( _
    ByVal setDisplayName As String, _
    ByVal setInternalName As String) As Boolean

    Dim displayUpper As String = _
        If(setDisplayName, "").Trim().ToUpperInvariant()

    If displayUpper.Contains("PRIVATE") Then Return True
    If displayUpper.Contains("THUMBNAIL") Then Return True
    Return False
End Function

Public Shared Function IsDefaultProperty(ByVal propertyName As String) As Boolean
    Select Case If(propertyName, "").Trim().ToUpperInvariant()
        Case "PART NUMBER", _
             "DESCRIPTION", _
             "MATERIAL", _
             "STOCK NUMBER", _
             "REVISION NUMBER"
            Return True
    End Select

    Return False
End Function

Public Shared Function CompareBomItems( _
    ByVal firstItem As PartBomItem, _
    ByVal secondItem As PartBomItem) As Integer

    Dim firstText As String = ""
    Dim secondText As String = ""

    If firstItem IsNot Nothing Then firstText = firstItem.PartNumber
    If secondItem IsNot Nothing Then secondText = secondItem.PartNumber

    Return String.Compare( _
        firstText, _
        secondText, _
        StringComparison.OrdinalIgnoreCase)
End Function

Public Shared Function ComparePropertyColumns( _
    ByVal firstProperty As PropertyColumnInfo, _
    ByVal secondProperty As PropertyColumnInfo) As Integer

    If firstProperty Is Nothing AndAlso secondProperty Is Nothing Then Return 0
    If firstProperty Is Nothing Then Return 1
    If secondProperty Is Nothing Then Return -1

    Dim firstPriority As Integer = _
        GetPropertyPriority(firstProperty.PropertyName)

    Dim secondPriority As Integer = _
        GetPropertyPriority(secondProperty.PropertyName)

    If firstPriority <> secondPriority Then
        Return firstPriority.CompareTo(secondPriority)
    End If

    Return String.Compare( _
        firstProperty.DisplayText, _
        secondProperty.DisplayText, _
        StringComparison.OrdinalIgnoreCase)
End Function

Public Shared Function GetPropertyPriority(ByVal propertyName As String) As Integer
    Select Case If(propertyName, "").Trim().ToUpperInvariant()
        Case "PART NUMBER" : Return 1
        Case "DESCRIPTION" : Return 2
        Case "MATERIAL" : Return 3
        Case "STOCK NUMBER" : Return 4
        Case "REVISION NUMBER" : Return 5
        Case Else : Return 100
    End Select
End Function

Public Shared Function GetRecommendedColumnWidth(ByVal propertyName As String) As Double
    Dim upperName As String = _
        If(propertyName, "").Trim().ToUpperInvariant()

    If upperName.Contains("DESCRIPTION") Then Return 38
    If upperName.Contains("PART NUMBER") Then Return 22
    If upperName.Contains("MATERIAL") Then Return 20

    If upperName.Contains("COMMENT") OrElse _
       upperName.Contains("NOTE") OrElse _
       upperName.Contains("GHI CHÚ") Then
        Return 32
    End If

    If upperName.Contains("DATE") Then Return 16
    If upperName.Contains("REVISION") Then Return 12

    If upperName.Contains("NUMBER") OrElse _
       upperName.Contains("CODE") Then
        Return 18
    End If

    Return 20
End Function

Function GetPropertyHorizontalAlignment(ByVal propertyName As String) As Integer
    Dim upperName As String = _
        If(propertyName, "").Trim().ToUpperInvariant()

    If upperName.Contains("DESCRIPTION") OrElse _
       upperName.Contains("COMMENT") OrElse _
       upperName.Contains("NOTE") OrElse _
       upperName.Contains("TITLE") OrElse _
       upperName.Contains("SUBJECT") Then
        Return -4131
    End If

    If upperName.Contains("PART NUMBER") OrElse _
       upperName.Contains("STOCK NUMBER") OrElse _
       upperName.Contains("MATERIAL") OrElse _
       upperName.Contains("REVISION") OrElse _
       upperName.Contains("CODE") Then
        Return -4108
    End If

    Return -4131
End Function

Function ShouldWrapProperty(ByVal propertyName As String) As Boolean
    Dim upperName As String = _
        If(propertyName, "").Trim().ToUpperInvariant()

    Return upperName.Contains("DESCRIPTION") OrElse _
           upperName.Contains("COMMENT") OrElse _
           upperName.Contains("NOTE") OrElse _
           upperName.Contains("TITLE") OrElse _
           upperName.Contains("SUBJECT")
End Function


Sub WriteFastSummarySheet(ByVal workbook As Object, ByVal bomItems As List(Of PartBomItem))
    If workbook Is Nothing OrElse bomItems Is Nothing Then Exit Sub
    Try
        Dim materialMap As New Dictionary(Of String, Integer)(StringComparer.OrdinalIgnoreCase)
        Dim vendorMap As New Dictionary(Of String, Integer)(StringComparer.OrdinalIgnoreCase)
        Dim revisionMap As New Dictionary(Of String, Integer)(StringComparer.OrdinalIgnoreCase)
        Dim totalQty As Integer = 0
        Dim totalMass As Double = 0
        For Each item As PartBomItem In bomItems
            If item Is Nothing Then Continue For
            totalQty += item.Quantity
            totalMass += item.Mass * item.Quantity
            IncrementSummary(materialMap, If(String.IsNullOrWhiteSpace(item.Material), "(EMPTY)", item.Material), item.Quantity)
            IncrementSummary(vendorMap, If(String.IsNullOrWhiteSpace(item.Vendor), "(EMPTY)", item.Vendor), item.Quantity)
            IncrementSummary(revisionMap, If(String.IsNullOrWhiteSpace(item.Revision), "(EMPTY)", item.Revision), item.Quantity)
        Next
        Dim rows As Integer = 5 + materialMap.Count + vendorMap.Count + revisionMap.Count
        Dim data(rows - 1, 2) As Object
        Dim r As Integer = 0
        data(r, 0) = "BOM SUMMARY" : r += 1
        data(r, 0) = "Unique Parts" : data(r, 1) = bomItems.Count : r += 1
        data(r, 0) = "Total Quantity" : data(r, 1) = totalQty : r += 1
        data(r, 0) = "Total Mass (" & BomUnitManager.MassUnit & ")" : data(r, 1) = BomUnitManager.ConvertMass(totalMass) : r += 1
        data(r, 0) = "MATERIAL" : data(r, 1) = "QTY" : r += 1
        For Each pair As KeyValuePair(Of String, Integer) In materialMap
            data(r, 0) = pair.Key : data(r, 1) = pair.Value : r += 1
        Next
        data(r, 0) = "VENDOR" : data(r, 1) = "QTY" : r += 1
        For Each pair As KeyValuePair(Of String, Integer) In vendorMap
            data(r, 0) = pair.Key : data(r, 1) = pair.Value : r += 1
        Next
        data(r, 0) = "REVISION" : data(r, 1) = "QTY" : r += 1
        For Each pair As KeyValuePair(Of String, Integer) In revisionMap
            data(r, 0) = pair.Key : data(r, 1) = pair.Value : r += 1
        Next
        Dim ws As Object = workbook.Worksheets.Add()
        ws.Name = "SUMMARY"
        ws.Range("A1", "C" & rows.ToString()).NumberFormat = "@"
        ws.Range("A1", "C" & rows.ToString()).Value2 = data
        ws.Columns("A:C").ColumnWidth = 24
        ws.Rows(1).Font.Bold = True
    Catch
        'Summary không được phép làm hỏng quá trình xuất BOM chính.
    End Try
End Sub

Sub IncrementSummary(ByVal map As Dictionary(Of String, Integer), ByVal key As String, ByVal quantity As Integer)
    If map.ContainsKey(key) Then map(key) += quantity Else map(key) = quantity
End Sub

Function ExcelColumnLetter(ByVal columnNumber As Integer) As String
    Dim dividend As Integer = columnNumber
    Dim columnName As String = ""

    While dividend > 0
        Dim modulo As Integer = (dividend - 1) Mod 26
        columnName = Chr(65 + modulo) & columnName
        dividend = CInt(Math.Floor(CDbl(dividend - modulo) / 26))
    End While

    Return columnName
End Function

Function RGBValue( _
    ByVal red As Integer, _
    ByVal green As Integer, _
    ByVal blue As Integer) As Integer

    Return red + (green * 256) + (blue * 65536)
End Function

Sub ReleaseComObject(ByVal comObject As Object)
    If comObject Is Nothing Then Exit Sub

    Try
        If Marshal.IsComObject(comObject) Then
            Marshal.FinalReleaseComObject(comObject)
        End If
    Catch
    End Try
End Sub

'====================================================================
' CORE CACHE - CHỈ ĐỌC INVENTOR MỘT LẦN CHO MỖI UNIQUE PART
'====================================================================

'####################################################################
' SECTION 09 - CORE DATA CACHE / GEOMETRY
' Cache dữ liệu cốt lõi, khối lượng, hình học, thickness và bounding box.
'####################################################################

Sub CacheCorePartData(ByVal item As PartBomItem)
    If item Is Nothing OrElse item.Document Is Nothing Then Exit Sub
    BomPerformanceCounters.CoreCacheCalls += 1
    BomPerformanceCounters.DocumentAccess += 1
    Dim doc As Inventor.Document = item.Document

    'PHASE 1 / PERFORMANCE CORE 2.0:
    'Core scan chỉ đọc dữ liệu BOM nhẹ. Geometry/Mass/RangeBox được tách sang BomGeometryEngine.
    item.Description = ReadPropertyByNames(doc, New String() {"Description"})
    item.Material = ReadPropertyByNames(doc, New String() {"Material"})
    item.Vendor = ReadPropertyByNames(doc, New String() {"Vendor", "Supplier"})
    item.Revision = ReadPropertyByNames(doc, New String() {"Revision Number", "Revision"})
    item.StockNumber = ReadPropertyByNames(doc, New String() {"Stock Number"})
    item.Project = ReadPropertyByNames(doc, New String() {"Project"})
    item.Category = ReadPropertyByNames(doc, New String() {"Category"})

    Try
        item.IsReadOnly = doc.FileSaveCounter < 0
    Catch
        item.IsReadOnly = False
    End Try
    Try
        item.IsUnsaved = String.IsNullOrWhiteSpace(doc.FullFileName)
    Catch
        item.IsUnsaved = True
    End Try

    'Chỉ nhận dạng Sheet Metal bằng type; không gọi MassProperties/RangeBox ở Core Scan.
    Try
        Dim pDoc As PartDocument = TryCast(doc, PartDocument)
        If pDoc IsNot Nothing AndAlso pDoc.ComponentDefinition IsNot Nothing Then
            item.IsSheetMetal = TypeOf pDoc.ComponentDefinition Is SheetMetalComponentDefinition
        End If
    Catch
        item.IsSheetMetal = False
    End Try

    Dim classificationText As String = (item.FileName & " " & item.PartNumber & " " & item.Description & " " & item.Category).ToUpperInvariant()
    item.IsPurchased = classificationText.Contains("PURCHASE") OrElse classificationText.Contains("MUA NGOÀI") OrElse classificationText.Contains("BEARING") OrElse classificationText.Contains("MOTOR")
    item.SearchBlob = (item.FileName & "|" & item.FilePath & "|" & item.PartNumber & "|" & item.Description & "|" & item.Material & "|" & item.Vendor & "|" & item.Revision & "|" & item.StockNumber & "|" & item.Project & "|" & item.Category & "|" & item.GetParentAssemblyText()).ToUpperInvariant()
    BomSignatureEngine.CaptureIntoItem(item)
End Sub

Public Class BomGeometryEngine
    Public Shared Sub EnsureLoaded(ByVal item As PartBomItem)
        If item Is Nothing Then Exit Sub
        If String.Equals(item.GeometryLoadState, "LOADED", StringComparison.OrdinalIgnoreCase) Then Exit Sub
        If String.Equals(item.GeometryLoadState, "LOADING", StringComparison.OrdinalIgnoreCase) Then Exit Sub
        item.GeometryLoadState = "LOADING"
        item.GeometryLoadError = ""
        Dim sw As Stopwatch = Stopwatch.StartNew()
        Try
            Dim pDoc As PartDocument = TryCast(item.Document, PartDocument)
            If pDoc Is Nothing OrElse pDoc.ComponentDefinition Is Nothing Then
                item.GeometryLoadState = "FAILED"
                item.GeometryLoadError = "Part document/component definition unavailable."
                Exit Sub
            End If
            Dim pDef As PartComponentDefinition = pDoc.ComponentDefinition
            item.IsSheetMetal = TypeOf pDef Is SheetMetalComponentDefinition
            Try
                Dim mp As MassProperties = pDef.MassProperties
                item.Mass = mp.Mass
                item.Volume = mp.Volume
                item.SurfaceArea = mp.Area
            Catch ex As Exception
                BomLogger.Warn("GEOMETRY_MASS", ex.Message, item)
            End Try
            Try
                Dim box As Box = pDef.RangeBox
                Dim dx As Double = Math.Abs(box.MaxPoint.X - box.MinPoint.X) * 10.0
                Dim dy As Double = Math.Abs(box.MaxPoint.Y - box.MinPoint.Y) * 10.0
                Dim dz As Double = Math.Abs(box.MaxPoint.Z - box.MinPoint.Z) * 10.0
                Dim dims As New List(Of Double)(New Double() {dx, dy, dz})
                dims.Sort()
                item.BoundingMinMm = dims(0) : item.BoundingMidMm = dims(1) : item.BoundingMaxMm = dims(2)
                item.BoundingBoxText = Math.Round(item.BoundingMaxMm, 2).ToString("0.##") & " x " & Math.Round(item.BoundingMidMm, 2).ToString("0.##") & " x " & Math.Round(item.BoundingMinMm, 2).ToString("0.##")
            Catch ex As Exception
                BomLogger.Warn("GEOMETRY_RANGEBOX", ex.Message, item)
            End Try
            If item.IsSheetMetal Then
                Try
                    Dim smDef As SheetMetalComponentDefinition = CType(pDef, SheetMetalComponentDefinition)
                    item.Thickness = smDef.Thickness.Value * 10.0
                    item.ThicknessSource = "SHEET METAL"
                    item.GeometryType = "SHEET METAL / PLATE"
                Catch ex As Exception
                    BomLogger.Warn("GEOMETRY_THICKNESS", ex.Message, item)
                End Try
            Else
                If item.BoundingMinMm > 0 AndAlso item.BoundingMidMm > 0 Then
                    Dim text As String = (item.FileName & " " & item.PartNumber & " " & item.Description & " " & item.Category).ToUpperInvariant()
                    Dim keywordPlate As Boolean = text.Contains("PLATE") OrElse text.Contains("TAM") OrElse text.Contains("TẤM") OrElse text.Contains("BASE") OrElse text.Contains("GUSSET") OrElse text.Contains("BRACKET") OrElse text.Contains("LEG") OrElse text.Contains("CHAN") OrElse text.Contains("CHÂN")
                    Dim thinRatio As Double = item.BoundingMinMm / Math.Max(item.BoundingMidMm, 0.0001)
                    If thinRatio <= 0.25 OrElse (keywordPlate AndAlso thinRatio <= 0.5) Then
                        item.Thickness = item.BoundingMinMm
                        item.ThicknessSource = "BOUNDING BOX"
                        item.GeometryType = If(keywordPlate, "PLATE / LEG", "THIN PART")
                    Else
                        item.Thickness = 0 : item.ThicknessSource = "" : item.GeometryType = "GENERAL PART"
                    End If
                Else
                    item.GeometryType = "UNKNOWN"
                End If
            End If
            item.GeometryLoadState = "LOADED"
            item.GeometryLoadedAt = DateTime.Now
        Catch ex As Exception
            item.GeometryLoadState = "FAILED"
            item.GeometryLoadError = ex.Message
            BomLogger.Warn("GEOMETRY", ex.Message, item)
        Finally
            sw.Stop()
            BomPerformanceCounters.AddGeometryLoad(sw.ElapsedMilliseconds)
        End Try
    End Sub

    Public Shared Sub Invalidate(ByVal item As PartBomItem)
        If item Is Nothing Then Exit Sub
        item.GeometryLoadState = "NOT LOADED"
        item.GeometryLoadError = ""
        item.GeometryLoadedAt = DateTime.MinValue
        item.Mass = 0 : item.Volume = 0 : item.SurfaceArea = 0
        item.Thickness = 0 : item.ThicknessSource = "" : item.GeometryType = ""
        item.BoundingMinMm = 0 : item.BoundingMidMm = 0 : item.BoundingMaxMm = 0 : item.BoundingBoxText = ""
    End Sub
End Class

Public Class BomPerformanceCounters
    Public Shared GeometryLoads As Integer = 0
    Public Shared GeometryMs As Long = 0
    Public Shared DocumentAccess As Long = 0
    Public Shared PropertyRead As Long = 0
    Public Shared OccurrenceTraversal As Long = 0
    Public Shared SignatureChecks As Long = 0
    Public Shared DrawingSearch As Long = 0
    Public Shared GridRefresh As Long = 0
    Public Shared CoreCacheCalls As Long = 0
    Public Shared PropertyReadMs As Long = 0
    Public Shared DrawingIndexMs As Long = 0
    Public Shared GridBuildMs As Long = 0
    Public Shared InitialLoadMs As Long = 0

    Public Shared Sub AddGeometryLoad(ByVal elapsedMs As Long)
        GeometryLoads += 1
        GeometryMs += Math.Max(0, elapsedMs)
    End Sub

    Public Shared Sub Reset()
        GeometryLoads = 0 : GeometryMs = 0
        DocumentAccess = 0 : PropertyRead = 0 : OccurrenceTraversal = 0
        SignatureChecks = 0 : DrawingSearch = 0 : GridRefresh = 0
        CoreCacheCalls = 0 : PropertyReadMs = 0 : DrawingIndexMs = 0 : GridBuildMs = 0
        InitialLoadMs = 0
    End Sub
End Class

Public Class BomMemorySnapshot
    Public ManagedBytes As Long
    Public WorkingSetBytes As Long
    Public CachedItems As Integer
    Public CachedOccurrences As Integer
    Public CachedGeometry As Integer
    Public CachedThumbnails As Integer

    Public Shared Function Capture(ByVal items As List(Of PartBomItem), ByVal occurrenceCount As Integer, ByVal thumbnailCount As Integer) As BomMemorySnapshot
        Dim s As New BomMemorySnapshot()
        Try : s.ManagedBytes = GC.GetTotalMemory(False) : Catch : End Try
        Try : s.WorkingSetBytes = Process.GetCurrentProcess().WorkingSet64 : Catch : End Try
        s.CachedItems = If(items Is Nothing, 0, items.Count)
        s.CachedOccurrences = Math.Max(0, occurrenceCount)
        s.CachedThumbnails = Math.Max(0, thumbnailCount)
        If items IsNot Nothing Then
            For Each item As PartBomItem In items
                If item IsNot Nothing AndAlso String.Equals(item.GeometryLoadState, "LOADED", StringComparison.OrdinalIgnoreCase) Then s.CachedGeometry += 1
            Next
        End If
        Return s
    End Function

    Public Shared Function FormatMB(ByVal bytes As Long) As String
        If bytes <= 0 Then Return "0 MB"
        Return (CDbl(bytes) / 1024.0 / 1024.0).ToString("0.0") & " MB"
    End Function
End Class

Function FormatGeometryNumber(ByVal valueMm As Double) As String
    If valueMm <= 0 Then Return ""
    Return Math.Round(valueMm, 2).ToString("0.##")
End Function

Sub DetectPlateThicknessFromBoundingBox(ByVal item As PartBomItem)
    If item Is Nothing Then Exit Sub
    If item.BoundingMinMm <= 0 OrElse item.BoundingMidMm <= 0 Then
        item.GeometryType = "UNKNOWN"
        Exit Sub
    End If

    Dim text As String = (item.FileName & " " & item.PartNumber & " " & item.Description & " " & item.Category).ToUpperInvariant()
    Dim keywordPlate As Boolean = text.Contains("PLATE") OrElse text.Contains("TAM") OrElse text.Contains("TẤM") OrElse text.Contains("BASE") OrElse text.Contains("GUSSET") OrElse text.Contains("BRACKET") OrElse text.Contains("LEG") OrElse text.Contains("CHAN") OrElse text.Contains("CHÂN")
    Dim thinRatio As Double = item.BoundingMinMm / Math.Max(item.BoundingMidMm, 0.0001)

    'Chi tiết mỏng rõ ràng hoặc có từ khóa plate/chân: lấy cạnh nhỏ nhất làm thickness ước lượng.
    If thinRatio <= 0.25 OrElse (keywordPlate AndAlso thinRatio <= 0.5) Then
        item.Thickness = item.BoundingMinMm
        item.ThicknessSource = "BOUNDING BOX"
        item.GeometryType = If(keywordPlate, "PLATE / LEG", "THIN PART")
    Else
        item.Thickness = 0
        item.ThicknessSource = ""
        item.GeometryType = "GENERAL PART"
    End If
End Sub

Function ReadPropertyByNames(ByVal doc As Inventor.Document, ByVal names As String()) As String
    If doc Is Nothing OrElse names Is Nothing Then Return ""
    BomPerformanceCounters.DocumentAccess += 1
    For Each propertySet As Inventor.PropertySet In doc.PropertySets
        For Each propertyName As String In names
            BomPerformanceCounters.PropertyRead += 1
            Try
                Dim p As Inventor.Property = propertySet.Item(propertyName)
                If p IsNot Nothing AndAlso p.Value IsNot Nothing Then Return Convert.ToString(p.Value).Trim()
            Catch
            End Try
        Next
    Next
    Return ""
End Function



'####################################################################
' PRO MAX 2.0 - COMMAND SECURITY / WRITE GUARD / OPERATION CONTEXT
'####################################################################
Public Enum BomCommandType
    ReadOnlyCommand = 0
    WriteCommand = 1
    DestructiveCommand = 2
End Enum

Public Class BomOperationContext
    Public OperationName As String = ""
    Public Progress As Integer = 0
    Public Total As Integer = 0
    Public Current As Integer = 0
    Public CancelRequested As Boolean = False
    Public StartedAt As DateTime = DateTime.Now

    Public ReadOnly Property Percent As Integer
        Get
            If Total <= 0 Then Return 0
            Return Math.Max(0, Math.Min(100, CInt((CDbl(Current) / CDbl(Total)) * 100.0R)))
        End Get
    End Property
End Class

Public Class BomWriteGuard
    Public Shared Function CanExecute(ByVal safeMode As Boolean, ByVal commandType As BomCommandType) As Boolean
        If Not safeMode Then Return True
        Return commandType = BomCommandType.ReadOnlyCommand
    End Function

    Public Shared Function EnsureWriteAllowed(ByVal safeMode As Boolean,
                                              ByVal operationName As String,
                                              Optional ByVal commandType As BomCommandType = BomCommandType.WriteCommand) As Boolean
        If CanExecute(safeMode, commandType) Then Return True
        BomLogger.Warn("WRITE_GUARD", "Blocked in SAFE MODE: " & operationName)
        Return False
    End Function
End Class

Public Class BomCommandDefinition
    Public Id As String = ""
    Public Caption As String = ""
    Public ShortCaption As String = ""
    Public Workspace As String = ""
    Public GroupName As String = ""
    Public IconKey As String = ""
    Public Tooltip As String = ""
    Public Description As String = ""
    Public Shortcut As String = ""
    Public Keywords As String = ""
    Public CommandType As BomCommandType = BomCommandType.ReadOnlyCommand
    Public IsWriteOperation As Boolean = False
    Public IsDestructive As Boolean = False
    Public RequiresSelection As Boolean = False
    Public RequiresDocument As Boolean = False
    Public RequiresDrawing As Boolean = False
    Public RequiresPendingChanges As Boolean = False
    Public RequiresSnapshot As Boolean = False
    Public IsQuickAccess As Boolean = False
    Public ContextTarget As String = ""
    Public ContextGroup As String = ""
    Public Order As Integer = 0
    Public IsPrimary As Boolean = False
    Public Handler As EventHandler = Nothing
End Class

Public Class BomCommandRegistry
    Private Shared ReadOnly _commands As New Dictionary(Of String, BomCommandDefinition)(StringComparer.OrdinalIgnoreCase)

    Public Shared Sub Register(ByVal command As BomCommandDefinition)
        If command Is Nothing OrElse String.IsNullOrWhiteSpace(command.Id) Then Exit Sub
        _commands(command.Id) = command
    End Sub

    Public Shared Function GetCommand(ByVal id As String) As BomCommandDefinition
        If String.IsNullOrWhiteSpace(id) Then Return Nothing
        Dim result As BomCommandDefinition = Nothing
        If _commands.TryGetValue(id, result) Then Return result
        Return Nothing
    End Function

    Public Shared Function AllCommands() As List(Of BomCommandDefinition)
        Return New List(Of BomCommandDefinition)(_commands.Values)
    End Function

    Public Shared Function ForWorkspace(ByVal workspace As String) As List(Of BomCommandDefinition)
        Dim result As New List(Of BomCommandDefinition)()
        For Each cmd As BomCommandDefinition In _commands.Values
            If String.Equals(cmd.Workspace, workspace, StringComparison.OrdinalIgnoreCase) Then result.Add(cmd)
        Next
        result.Sort(Function(a As BomCommandDefinition, b As BomCommandDefinition) As Integer
                        Dim g As Integer = String.Compare(a.GroupName, b.GroupName, StringComparison.OrdinalIgnoreCase)
                        If g <> 0 Then Return g
                        Return a.Order.CompareTo(b.Order)
                    End Function)
        Return result
    End Function

    Public Shared Sub Clear()
        _commands.Clear()
    End Sub
End Class

Public Class BomIconCache
    Private Shared ReadOnly _cache As New Dictionary(Of String, System.Drawing.Image)(StringComparer.OrdinalIgnoreCase)

    Public Shared Function GetOrCreate(ByVal key As String, ByVal factory As Func(Of System.Drawing.Image)) As System.Drawing.Image
        Dim normalized As String = If(key, "").Trim().ToUpperInvariant()
        If normalized = "" Then normalized = "DEFAULT"
        Dim img As System.Drawing.Image = Nothing
        If _cache.TryGetValue(normalized, img) AndAlso img IsNot Nothing Then
            Return CType(img.Clone(), System.Drawing.Image)
        End If
        img = factory()
        If img IsNot Nothing Then
            _cache(normalized) = CType(img.Clone(), System.Drawing.Image)
            Return img
        End If
        Return Nothing
    End Function

    Public Shared Sub Clear()
        For Each img As System.Drawing.Image In _cache.Values
            Try
                If img IsNot Nothing Then img.Dispose()
            Catch
            End Try
        Next
        _cache.Clear()
    End Sub
End Class


'####################################################################
' PRO MAX FOUNDATION - CENTRAL POLICY / CONFIG / CONSTANTS / SESSION
'####################################################################
Public Enum BomErrorSeverity
    IgnoreSafe = 0
    LogOnly = 1
    Warning = 2
    [Error] = 3
    Fatal = 4
End Enum

Public Class BomOperationResult
    Public Success As Boolean = True
    Public Severity As BomErrorSeverity = BomErrorSeverity.LogOnly
    Public Engine As String = ""
    Public Operation As String = ""
    Public Message As String = ""
    Public ExceptionText As String = ""

    Public Shared Function Ok(ByVal engineName As String, ByVal operationName As String) As BomOperationResult
        Dim r As New BomOperationResult()
        r.Engine = If(engineName, "")
        r.Operation = If(operationName, "")
        Return r
    End Function

    Public Shared Function Fail(ByVal engineName As String,
                                ByVal operationName As String,
                                ByVal messageText As String,
                                ByVal severityValue As BomErrorSeverity,
                                Optional ByVal ex As Exception = Nothing) As BomOperationResult
        Dim r As New BomOperationResult()
        r.Success = False
        r.Engine = If(engineName, "")
        r.Operation = If(operationName, "")
        r.Message = If(messageText, "")
        r.Severity = severityValue
        If ex IsNot Nothing Then r.ExceptionText = ex.ToString()
        Return r
    End Function
End Class

Public Class BomErrorPolicy
    Public Shared Function CanContinue(ByVal severity As BomErrorSeverity) As Boolean
        Return severity <> BomErrorSeverity.Fatal
    End Function

    Public Shared Sub Report(ByVal result As BomOperationResult, Optional ByVal item As PartBomItem = Nothing)
        If result Is Nothing OrElse result.Success Then Exit Sub
        Select Case result.Severity
            Case BomErrorSeverity.IgnoreSafe
                'Optional failure: intentionally silent.
            Case BomErrorSeverity.LogOnly
                BomLogger.Info(result.Engine & "/" & result.Operation, result.Message)
            Case BomErrorSeverity.Warning
                BomLogger.Warn(result.Engine & "/" & result.Operation, result.Message, item)
            Case Else
                BomLogger.Error(result.Engine & "/" & result.Operation,
                                result.Message & If(String.IsNullOrWhiteSpace(result.ExceptionText), "", " | " & result.ExceptionText),
                                item)
        End Select
    End Sub
End Class

Public Class BomConstants
    Public Const ToolVersion As String = "BOM TOOL PRO MAX 10.3 SAFE ASSEMBLY SWITCH"
    Public Const StatusOk As String = "OK"
    Public Const StatusWarning As String = "WARNING"
    Public Const StatusError As String = "ERROR"
    Public Const StatusPending As String = "PENDING"
    Public Const DefaultScanMode As String = "NORMAL"
End Class

Public Class BomConfig
    Public SafeModeDefault As Boolean = False
    Public AtomicTransactionDefault As Boolean = True
    Public EnableSessionPersistence As Boolean = True
    Public EnablePerformanceMonitoring As Boolean = True
    Public EnableMemoryMonitoring As Boolean = True
    Public SearchDebounceMs As Integer = 220
End Class

Public Class BomSessionState
    Public AssemblyPath As String = ""
    Public DisplayMode As String = "HYBRID"
    Public ScanMode As String = "NORMAL"
    Public SearchText As String = ""
    Public AssemblyFilter As String = ""
    Public QuickFilter As String = "ALL"
    Public ActiveWorkspace As String = "HOME"
    Public SafeMode As Boolean = False
    Public WindowWidth As Integer = 1440
    Public WindowHeight As Integer = 860
    Public WindowLeft As Integer = -1
    Public WindowTop As Integer = -1
    Public RibbonCollapsed As Boolean = False
    Public DetailPanelVisible As Boolean = True
    Public DetailPanelWidth As Integer = 340
    Public SelectedProfile As String = "ENGINEERING"

    Private Shared Function E(ByVal value As String) As String
        Return Convert.ToBase64String(System.Text.Encoding.UTF8.GetBytes(If(value, "")))
    End Function

    Private Shared Function D(ByVal value As String) As String
        Try
            Return System.Text.Encoding.UTF8.GetString(Convert.FromBase64String(If(value, "")))
        Catch
            Return ""
        End Try
    End Function

    Public Sub Save(ByVal filePath As String)
        If String.IsNullOrWhiteSpace(filePath) Then Exit Sub
        Dim lines As New List(Of String)()
        lines.Add("ASSEMBLY=" & E(AssemblyPath))
        lines.Add("DISPLAY=" & E(DisplayMode))
        lines.Add("SCAN=" & E(ScanMode))
        lines.Add("SEARCH=" & E(SearchText))
        lines.Add("FILTER=" & E(AssemblyFilter))
        lines.Add("QUICK=" & E(QuickFilter))
        lines.Add("WORKSPACE=" & E(ActiveWorkspace))
        lines.Add("SAFE=" & SafeMode.ToString())
        lines.Add("WIDTH=" & WindowWidth.ToString())
        lines.Add("HEIGHT=" & WindowHeight.ToString())
        lines.Add("LEFT=" & WindowLeft.ToString())
        lines.Add("TOP=" & WindowTop.ToString())
        lines.Add("RIBBONCOLLAPSED=" & RibbonCollapsed.ToString())
        lines.Add("DETAILVISIBLE=" & DetailPanelVisible.ToString())
        lines.Add("DETAILWIDTH=" & DetailPanelWidth.ToString())
        lines.Add("PROFILE=" & E(SelectedProfile))
        System.IO.File.WriteAllLines(filePath, lines.ToArray(), System.Text.Encoding.UTF8)
    End Sub

    Public Shared Function Load(ByVal filePath As String) As BomSessionState
        Dim s As New BomSessionState()
        If String.IsNullOrWhiteSpace(filePath) OrElse Not System.IO.File.Exists(filePath) Then Return s
        Try
            For Each line As String In System.IO.File.ReadAllLines(filePath, System.Text.Encoding.UTF8)
                Dim p As Integer = line.IndexOf("="c)
                If p <= 0 Then Continue For
                Dim key As String = line.Substring(0, p).Trim().ToUpperInvariant()
                Dim value As String = line.Substring(p + 1)
                Select Case key
                    Case "ASSEMBLY", "STRUCTURE" : s.AssemblyPath = D(value)
                    Case "DISPLAY" : s.DisplayMode = D(value)
                    Case "SCAN" : s.ScanMode = D(value)
                    Case "SEARCH" : s.SearchText = D(value)
                    Case "FILTER" : s.AssemblyFilter = D(value)
                    Case "QUICK" : s.QuickFilter = D(value)
                    Case "WORKSPACE" : s.ActiveWorkspace = D(value)
                    Case "SAFE" : Boolean.TryParse(value, s.SafeMode)
                    Case "WIDTH" : Integer.TryParse(value, s.WindowWidth)
                    Case "HEIGHT" : Integer.TryParse(value, s.WindowHeight)
                    Case "LEFT" : Integer.TryParse(value, s.WindowLeft)
                    Case "TOP" : Integer.TryParse(value, s.WindowTop)
                    Case "RIBBONCOLLAPSED" : Boolean.TryParse(value, s.RibbonCollapsed)
                    Case "DETAILVISIBLE" : Boolean.TryParse(value, s.DetailPanelVisible)
                    Case "DETAILWIDTH" : Integer.TryParse(value, s.DetailPanelWidth)
                    Case "PROFILE" : s.SelectedProfile = D(value)
                End Select
            Next
        Catch ex As Exception
            BomLogger.Warn("SESSION", "Không đọc được session: " & ex.Message)
        End Try
        Return s
    End Function
End Class



'####################################################################
' SINGLE INSTANCE MANAGER
' Prevents multiple BOM Tool windows/runtimes in the same Inventor process.
' Second launch activates the existing window instead of rebuilding engines.
'####################################################################
Public Class BomSingleInstanceManager
    Private Shared _activeForm As System.Windows.Forms.Form = Nothing
    Private Shared ReadOnly _syncRoot As New Object()

    Public Shared Function TryActivateExisting() As Boolean
        SyncLock _syncRoot
            Try
                If _activeForm Is Nothing Then Return False
                If _activeForm.IsDisposed OrElse _activeForm.Disposing Then
                    _activeForm = Nothing
                    Return False
                End If

                If Not _activeForm.IsHandleCreated Then
                    Return False
                End If

                Try
                    If _activeForm.WindowState = System.Windows.Forms.FormWindowState.Minimized Then
                        _activeForm.WindowState = System.Windows.Forms.FormWindowState.Normal
                    End If
                Catch
                End Try

                Try
                    _activeForm.Show()
                Catch
                End Try

                Try
                    _activeForm.BringToFront()
                    _activeForm.Activate()
                    _activeForm.Focus()
                Catch
                End Try

                Return True
            Catch
                _activeForm = Nothing
                Return False
            End Try
        End SyncLock
    End Function

    Public Shared Sub Register(ByVal form As System.Windows.Forms.Form)
        If form Is Nothing Then Exit Sub
        SyncLock _syncRoot
            _activeForm = form
        End SyncLock
    End Sub

    Public Shared Sub Unregister(ByVal form As System.Windows.Forms.Form)
        SyncLock _syncRoot
            If _activeForm Is form Then _activeForm = Nothing
        End SyncLock
    End Sub

    Public Shared Function HasActiveInstance() As Boolean
        SyncLock _syncRoot
            If _activeForm Is Nothing Then Return False
            Return Not _activeForm.IsDisposed AndAlso Not _activeForm.Disposing
        End SyncLock
    End Function
End Class


'====================================================================
' DATA CLASSES
'====================================================================

'####################################################################
' SECTION 10 - PRIMARY BOM DATA MODELS
' PartBomItem, RuntimeIndex, PropertyColumnInfo và dữ liệu trạng thái.
'####################################################################

Public Enum BomLogLevel
    Info = 0
    Warning = 1
    [Error] = 2
End Enum

Public Class BomLogEntry
    Public Time As DateTime = DateTime.Now
    Public Level As BomLogLevel = BomLogLevel.Info
    Public ModuleName As String = ""
    Public Operation As String = ""
    Public ExceptionText As String = ""
    Public FilePath As String = ""
    Public PartNumber As String = ""
    Public Message As String = ""

    Public Overrides Function ToString() As String
        Return Time.ToString("HH:mm:ss") & " | " & Level.ToString().ToUpperInvariant() & " | " & _
               ModuleName & If(String.IsNullOrWhiteSpace(Operation), "", "/" & Operation) & " | " & PartNumber & " | " & FilePath & " | " & Message & If(String.IsNullOrWhiteSpace(ExceptionText), "", " | EX: " & ExceptionText)
    End Function
End Class

Public Class BomLogger
    Private Shared _entries As New List(Of BomLogEntry)()
    Private Shared _sessionStarted As DateTime = DateTime.Now

    Public Shared Sub Reset()
        _entries.Clear()
        _sessionStarted = DateTime.Now
    End Sub

    Public Shared Sub Add(ByVal level As BomLogLevel, ByVal moduleName As String, ByVal message As String, Optional ByVal item As PartBomItem = Nothing, Optional ByVal filePath As String = "")
        Try
            Dim e As New BomLogEntry()
            e.Time = DateTime.Now
            e.Level = level
            e.ModuleName = If(moduleName, "")
            e.Message = If(message, "")
            If item IsNot Nothing Then
                e.FilePath = If(item.FilePath, "")
                e.PartNumber = If(item.PartNumber, "")
            Else
                e.FilePath = If(filePath, "")
            End If
            _entries.Add(e)
        Catch
            'Logger tuyệt đối không được làm dừng Rule.
        End Try
    End Sub

    Public Shared Sub Info(ByVal moduleName As String, ByVal message As String)
        Add(BomLogLevel.Info, moduleName, message)
    End Sub

    Public Shared Sub Warn(ByVal moduleName As String, ByVal message As String, Optional ByVal item As PartBomItem = Nothing)
        Add(BomLogLevel.Warning, moduleName, message, item)
    End Sub

    Public Shared Sub [Error](ByVal moduleName As String, ByVal message As String, Optional ByVal item As PartBomItem = Nothing)
        Add(BomLogLevel.[Error], moduleName, message, item)
    End Sub

    Public Shared Sub Log(ByVal moduleName As String,
                          ByVal filePath As String,
                          ByVal operationName As String,
                          ByVal severity As String,
                          ByVal message As String)
        Dim level As BomLogLevel = BomLogLevel.Info
        Dim s As String = If(severity, "").Trim().ToUpperInvariant()
        If s = "ERROR" OrElse s = "CRITICAL" Then
            level = BomLogLevel.[Error]
        ElseIf s = "WARNING" OrElse s = "WARN" Then
            level = BomLogLevel.Warning
        End If
        Add(level, If(moduleName, "") & If(String.IsNullOrWhiteSpace(operationName), "", "/" & operationName),
            If(message, ""), Nothing, If(filePath, ""))
    End Sub

    Public Shared Function Count(ByVal level As BomLogLevel) As Integer
        Dim n As Integer = 0
        For Each e As BomLogEntry In _entries
            If e.Level = level Then n += 1
        Next
        Return n
    End Function

    Public Shared Function Summary() As String
        Return "Log: " & _entries.Count.ToString() & _
               " | Warning: " & Count(BomLogLevel.Warning).ToString() & _
               " | Error: " & Count(BomLogLevel.[Error]).ToString()
    End Function

    Public Shared Function BuildText() As String
        Dim sb As New StringBuilder()
        sb.AppendLine("BOM TOOL PRO - SESSION LOG")
        sb.AppendLine("Started: " & _sessionStarted.ToString("dd/MM/yyyy HH:mm:ss"))
        sb.AppendLine(Summary())
        sb.AppendLine(New String("-"c, 90))
        For Each e As BomLogEntry In _entries
            sb.AppendLine(e.ToString())
        Next
        Return sb.ToString()
    End Function
End Class

Public Enum BomScanMode
    Fast = 0
    Normal = 1
    Deep = 2
End Enum

Public Class BomPerformanceSnapshot
    Public StartedAt As DateTime = DateTime.Now
    Public SmartRefreshMs As Long = 0
    Public SignatureChecks As Integer = 0
    Public CacheHits As Integer = 0
    Public CacheMisses As Integer = 0
    Public ChangedDocuments As Integer = 0
    Public LastMode As String = "NORMAL"

    Public Function HitRate() As Double
        Dim total As Integer = CacheHits + CacheMisses
        If total <= 0 Then Return 0
        Return (CDbl(CacheHits) / CDbl(total)) * 100.0
    End Function
End Class

Public Class BomSignatureEngine
    Public Shared Sub CaptureIntoItem(ByVal item As PartBomItem)
        If item Is Nothing Then Exit Sub
        item.SignaturePath = If(item.FilePath, "")
        item.SignaturePartNumber = If(item.PartNumber, "")
        item.SignatureRevision = If(item.Revision, "")
        item.SignatureBomStructure = If(item.BomStructureText, "")
        item.SignatureWriteTicks = 0
        item.SignatureFileSize = 0
        Try
            If Not String.IsNullOrWhiteSpace(item.FilePath) AndAlso System.IO.File.Exists(item.FilePath) Then
                Dim fi As New System.IO.FileInfo(item.FilePath)
                item.SignatureWriteTicks = fi.LastWriteTimeUtc.Ticks
                item.SignatureFileSize = fi.Length
            End If
        Catch ex As Exception
            BomLogger.Warn("SIGNATURE", ex.Message, item)
        End Try
        item.SignatureCapturedAt = DateTime.Now
        item.LastCacheState = "UNCHANGED"
    End Sub

    Public Shared Function HasChanged(ByVal item As PartBomItem) As Boolean
        If item Is Nothing Then Return True
        Try
            If String.IsNullOrWhiteSpace(item.FilePath) Then Return True
            If Not System.IO.File.Exists(item.FilePath) Then Return True
            Dim fi As New System.IO.FileInfo(item.FilePath)
            If item.SignatureCapturedAt = DateTime.MinValue Then Return True
            If fi.LastWriteTimeUtc.Ticks <> item.SignatureWriteTicks Then Return True
            If fi.Length <> item.SignatureFileSize Then Return True
            If item.Document IsNot Nothing AndAlso item.Document.Dirty Then Return True
            Return False
        Catch
            Return True
        End Try
    End Function

    Public Shared Function FileSignature(ByVal filePath As String) As String
        Try
            If String.IsNullOrWhiteSpace(filePath) OrElse Not System.IO.File.Exists(filePath) Then Return "MISSING"
            Dim fi As New System.IO.FileInfo(filePath)
            Return fi.FullName.ToUpperInvariant() & "|" & fi.LastWriteTimeUtc.Ticks.ToString() & "|" & fi.Length.ToString()
        Catch
            Return "ERROR"
        End Try
    End Function
End Class

Public Class PartBomItem
    Public DocumentKey As String
    Public Document As Inventor.Document
    Public Quantity As Integer
    Public FileName As String
    Public FilePath As String
    Public PartNumber As String

    'Core cache: đọc đúng một lần cho mỗi file Part.
    Public Description As String = ""
    Public Material As String = ""
    Public Vendor As String = ""
    Public Revision As String = ""
    Public StockNumber As String = ""
    Public Project As String = ""
    Public Category As String = ""
    Public Mass As Double = 0
    Public Volume As Double = 0
    Public SurfaceArea As Double = 0
    Public Thickness As Double = 0
    Public ThicknessSource As String = ""
    Public GeometryType As String = ""
    Public BoundingMinMm As Double = 0
    Public BoundingMidMm As Double = 0
    Public BoundingMaxMm As Double = 0
    Public BoundingBoxText As String = ""
    Public GeometryLoadState As String = "NOT LOADED"
    Public GeometryLoadError As String = ""
    Public GeometryLoadedAt As DateTime = DateTime.MinValue
    Public BomStructureText As String = ""

    'Compatibility properties used by the later engines.
    Public Property BomStructure As String
        Get
            Return If(BomStructureText, "")
        End Get
        Set(ByVal value As String)
            BomStructureText = If(value, "")
        End Set
    End Property

    Public SuppressedCount As Integer = 0
    Public DataStatus As String = ""

    Public IsReadOnly As Boolean = False
    Public IsUnsaved As Boolean = False
    Public IsAdaptive As Boolean = False
    Public IsVirtual As Boolean = False
    Public IsReference As Boolean = False
    Public IsSheetMetal As Boolean = False
    Public IsPurchased As Boolean = False
    Public SearchBlob As String = ""
    Public IsBomDirty As Boolean = False
    Public DirtyPropertyKeys As New HashSet(Of String)(StringComparer.OrdinalIgnoreCase)

    'V20 - CHANGE SIGNATURE / INCREMENTAL CACHE
    Public SignaturePath As String = ""
    Public SignatureWriteTicks As Long = 0
    Public SignatureFileSize As Long = 0
    Public SignaturePartNumber As String = ""
    Public SignatureRevision As String = ""
    Public SignatureBomStructure As String = ""
    Public SignatureCapturedAt As DateTime = DateTime.MinValue
    Public LastCacheState As String = "NEW"

    'On-demand feature cache. Chỉ Feature được gọi mới đọc Inventor.
    Public FeatureValues As New Dictionary(Of String, Object)(StringComparer.OrdinalIgnoreCase)
    Public LoadedFeatures As New HashSet(Of String)(StringComparer.OrdinalIgnoreCase)
    Public ThumbnailImage As System.Drawing.Image = Nothing

    'Occurrence cache giúp Highlight Part O(k), không quét lại toàn bộ cây Assembly.
    Public Occurrences As New List(Of ComponentOccurrence)()

    Public Sub AddOccurrence(ByVal occurrence As ComponentOccurrence)
        If occurrence Is Nothing Then Exit Sub
        Occurrences.Add(occurrence)
    End Sub

    Public SelectedPropertyValues As New Dictionary( _
        Of String, Object)(StringComparer.OrdinalIgnoreCase)

    Private ParentAssemblies As New SortedSet( _
        Of String)(StringComparer.OrdinalIgnoreCase)

    Private ParentAssemblyQuantities As New Dictionary( _
        Of String, Integer)(StringComparer.OrdinalIgnoreCase)

    'Đường dẫn Assembly đầy đủ, ví dụ ROOT\FRAME\WELDMENT.
    'Dùng để xuất Excel đúng cấu trúc mẹ-con mà không đọc lại Inventor.
    Private AssemblyPathQuantities As New Dictionary( _
        Of String, Integer)(StringComparer.OrdinalIgnoreCase)

    Public Sub AddParentAssembly(ByVal assemblyName As String)
        If String.IsNullOrWhiteSpace(assemblyName) Then Exit Sub
        Dim cleanName As String = assemblyName.Trim()
        ParentAssemblies.Add(cleanName)
        If ParentAssemblyQuantities.ContainsKey(cleanName) Then
            ParentAssemblyQuantities(cleanName) += 1
        Else
            ParentAssemblyQuantities(cleanName) = 1
        End If
    End Sub

    Public Sub AddAssemblyPath(ByVal assemblyPath As String)
        If String.IsNullOrWhiteSpace(assemblyPath) Then Exit Sub
        Dim cleanPath As String = assemblyPath.Trim().Trim("\"c)
        If cleanPath.Length = 0 Then Exit Sub
        If AssemblyPathQuantities.ContainsKey(cleanPath) Then
            AssemblyPathQuantities(cleanPath) += 1
        Else
            AssemblyPathQuantities(cleanPath) = 1
        End If
    End Sub

    Public Function GetAssemblyPaths() As List(Of String)
        Return New List(Of String)(AssemblyPathQuantities.Keys)
    End Function

    Public Function GetQuantityForAssemblyPath(ByVal assemblyPath As String) As Integer
        If String.IsNullOrWhiteSpace(assemblyPath) Then Return 0
        Dim cleanPath As String = assemblyPath.Trim().Trim("\"c)
        If AssemblyPathQuantities.ContainsKey(cleanPath) Then Return AssemblyPathQuantities(cleanPath)
        Return 0
    End Function

    Public Function GetParentAssemblyText() As String
        If ParentAssemblies.Count = 0 Then Return ""
        Return String.Join("; ", New List(Of String)(ParentAssemblies).ToArray())
    End Function

    Public Function GetParentAssemblies() As List(Of String)
        Return New List(Of String)(ParentAssemblies)
    End Function

    Public Function GetQuantityForParent(ByVal assemblyName As String) As Integer
        If String.IsNullOrWhiteSpace(assemblyName) Then Return 0
        If ParentAssemblyQuantities.ContainsKey(assemblyName) Then Return ParentAssemblyQuantities(assemblyName)
        Return 0
    End Function
End Class

Public Class BomRuntimeIndex
    Public ItemByKey As New Dictionary(Of String, PartBomItem)(StringComparer.OrdinalIgnoreCase)
    Public ItemsByAssembly As New SortedDictionary(Of String, List(Of PartBomItem))(StringComparer.OrdinalIgnoreCase)
    Public AssemblyQuantity As New Dictionary(Of String, Integer)(StringComparer.OrdinalIgnoreCase)
    Public TotalQuantity As Integer = 0
    Public TotalOccurrences As Integer = 0

    Public Sub Build(ByVal rootAssemblyName As String, ByVal items As List(Of PartBomItem))
        ItemByKey.Clear()
        ItemsByAssembly.Clear()
        AssemblyQuantity.Clear()
        TotalQuantity = 0
        TotalOccurrences = 0
        If items Is Nothing Then Exit Sub

        For Each item As PartBomItem In items
            If item Is Nothing Then Continue For
            If Not String.IsNullOrWhiteSpace(item.DocumentKey) AndAlso Not ItemByKey.ContainsKey(item.DocumentKey) Then
                ItemByKey.Add(item.DocumentKey, item)
            End If
            TotalQuantity += Math.Max(0, item.Quantity)
            If item.Occurrences IsNot Nothing Then TotalOccurrences += item.Occurrences.Count

            Dim parents As List(Of String) = item.GetParentAssemblies()
            If parents.Count = 0 AndAlso Not String.IsNullOrWhiteSpace(rootAssemblyName) Then parents.Add(rootAssemblyName)
            For Each parentName As String In parents
                If String.IsNullOrWhiteSpace(parentName) Then Continue For
                If Not ItemsByAssembly.ContainsKey(parentName) Then ItemsByAssembly(parentName) = New List(Of PartBomItem)()
                ItemsByAssembly(parentName).Add(item)
                Dim q As Integer = item.GetQuantityForParent(parentName)
                If q <= 0 AndAlso String.Equals(parentName, rootAssemblyName, StringComparison.OrdinalIgnoreCase) Then q = item.Quantity
                If AssemblyQuantity.ContainsKey(parentName) Then
                    AssemblyQuantity(parentName) += Math.Max(0, q)
                Else
                    AssemblyQuantity(parentName) = Math.Max(0, q)
                End If
            Next
        Next

        If Not String.IsNullOrWhiteSpace(rootAssemblyName) AndAlso Not ItemsByAssembly.ContainsKey(rootAssemblyName) Then
            ItemsByAssembly(rootAssemblyName) = New List(Of PartBomItem)(items)
            AssemblyQuantity(rootAssemblyName) = TotalQuantity
        End If
    End Sub

    Public Function BelongsToAssembly(ByVal item As PartBomItem, ByVal assemblyName As String, ByVal rootAssemblyName As String) As Boolean
        If item Is Nothing OrElse String.IsNullOrWhiteSpace(assemblyName) Then Return True
        If String.Equals(assemblyName, rootAssemblyName, StringComparison.OrdinalIgnoreCase) Then Return True
        Return item.GetQuantityForParent(assemblyName) > 0
    End Function
End Class


'####################################################################
' PHASE 4 - STRUCTURED BOM ENGINE
' PARTS ONLY / STRUCTURED / HYBRID + Quantity/BOM Structure foundation
'####################################################################
Public Enum BomDisplayMode
    PartsOnly = 0
    Structured = 1
    Hybrid = 2
End Enum

Public Class BomAssemblyPartEntry
    Public Item As PartBomItem
    Public LocalQuantity As Integer
End Class

Public Class BomAssemblyNode
    Public Name As String = ""
    Public FullPath As String = ""
    Public Level As Integer = 0
    Public Parent As BomAssemblyNode = Nothing
    Public Children As New Dictionary(Of String, BomAssemblyNode)(StringComparer.OrdinalIgnoreCase)
    Public DirectParts As New Dictionary(Of String, BomAssemblyPartEntry)(StringComparer.OrdinalIgnoreCase)

    Public Sub New(ByVal nodeName As String, ByVal nodePath As String, ByVal nodeLevel As Integer, ByVal parentNode As BomAssemblyNode)
        Name = If(nodeName, "")
        FullPath = If(nodePath, "")
        Level = Math.Max(0, nodeLevel)
        Parent = parentNode
    End Sub

    Public Function GetOrCreateChild(ByVal childName As String, ByVal childPath As String) As BomAssemblyNode
        Dim child As BomAssemblyNode = Nothing
        If Not Children.TryGetValue(childName, child) Then
            child = New BomAssemblyNode(childName, childPath, Level + 1, Me)
            Children.Add(childName, child)
        End If
        Return child
    End Function

    Public Sub AddDirectPart(ByVal item As PartBomItem, ByVal qty As Integer)
        If item Is Nothing Then Exit Sub
        Dim key As String = If(String.IsNullOrWhiteSpace(item.DocumentKey), item.FilePath, item.DocumentKey)
        If String.IsNullOrWhiteSpace(key) Then key = item.PartNumber & "|" & item.FileName
        Dim entry As BomAssemblyPartEntry = Nothing
        If DirectParts.TryGetValue(key, entry) Then
            entry.LocalQuantity += Math.Max(0, qty)
        Else
            entry = New BomAssemblyPartEntry()
            entry.Item = item
            entry.LocalQuantity = Math.Max(0, qty)
            DirectParts.Add(key, entry)
        End If
    End Sub

    Public Function GetSortedChildren() As List(Of BomAssemblyNode)
        Dim result As New List(Of BomAssemblyNode)(Children.Values)
        result.Sort(Function(a As BomAssemblyNode, b As BomAssemblyNode) StringComparer.OrdinalIgnoreCase.Compare(a.Name, b.Name))
        Return result
    End Function

    Public Function GetDirectEntries() As List(Of BomAssemblyPartEntry)
        Return New List(Of BomAssemblyPartEntry)(DirectParts.Values)
    End Function

    Public Function GetRecursiveQuantity() As Integer
        Dim total As Integer = 0
        For Each e As BomAssemblyPartEntry In DirectParts.Values
            If e Is Nothing OrElse e.Item Is Nothing Then Continue For
            If Not BomStructurePolicy.IsReference(e.Item) Then total += Math.Max(0, e.LocalQuantity)
        Next
        For Each child As BomAssemblyNode In Children.Values
            total += child.GetRecursiveQuantity()
        Next
        Return total
    End Function

    Public Function GetRecursiveUniquePartCount() As Integer
        Dim keys As New HashSet(Of String)(StringComparer.OrdinalIgnoreCase)
        CollectKeys(keys)
        Return keys.Count
    End Function

    Private Sub CollectKeys(ByVal keys As HashSet(Of String))
        For Each key As String In DirectParts.Keys
            keys.Add(key)
        Next
        For Each child As BomAssemblyNode In Children.Values
            child.CollectKeys(keys)
        Next
    End Sub
End Class


Public Class BomQuantityInfo
    Public LocalQty As Integer = 0
    Public ParentQty As Integer = 1
    Public EffectiveQty As Integer = 0
    Public TotalQty As Integer = 0
    Public VisibleQty As Integer = 0
    Public SuppressedQty As Integer = 0
End Class

Public Class BomQuantityEngine
    Public Shared Function ForItemInNode(ByVal item As PartBomItem, ByVal node As BomAssemblyNode) As BomQuantityInfo
        Dim q As New BomQuantityInfo()
        If item Is Nothing Then Return q
        q.TotalQty = Math.Max(0, item.Quantity)
        If node IsNot Nothing Then
            q.LocalQty = item.GetQuantityForAssemblyPath(node.FullPath)
            If q.LocalQty <= 0 Then q.LocalQty = item.GetQuantityForParent(node.Name)
            q.ParentQty = GetParentMultiplier(node)
        End If
        If q.LocalQty <= 0 Then q.LocalQty = q.TotalQty
        q.EffectiveQty = Math.Max(0, q.LocalQty * Math.Max(1, q.ParentQty))
        q.SuppressedQty = Math.Max(0, item.SuppressedCount)
        q.VisibleQty = Math.Max(0, q.TotalQty - q.SuppressedQty)
        Return q
    End Function

    Private Shared Function GetParentMultiplier(ByVal node As BomAssemblyNode) As Integer
        'AssemblyPath cache currently represents occurrence paths, therefore each concrete path
        'already contributes one parent occurrence. Keep multiplier explicit for future BOM-row qty.
        If node Is Nothing Then Return 1
        Return 1
    End Function
End Class

Public Class BomStructurePolicy
    Public Shared Function Normalize(ByVal value As String) As String
        Dim s As String = If(value, "").Trim().ToUpperInvariant()
        If s.Contains("PHANTOM") Then Return "PHANTOM"
        If s.Contains("REFERENCE") Then Return "REFERENCE"
        If s.Contains("PURCHASED") Then Return "PURCHASED"
        If s.Contains("INSEPARABLE") Then Return "INSEPARABLE"
        If s.Contains("NORMAL") Then Return "NORMAL"
        Return If(s.Length = 0, "NORMAL", s)
    End Function

    Public Shared Function IncludeInPartsOnly(ByVal item As PartBomItem) As Boolean
        If item Is Nothing Then Return False
        'Reference is excluded from normal Parts Only quantity rollup.
        Return Normalize(item.BomStructure) <> "REFERENCE"
    End Function

    Public Shared Function IsReference(ByVal item As PartBomItem) As Boolean
        Return item IsNot Nothing AndAlso Normalize(item.BomStructure) = "REFERENCE"
    End Function

    Public Shared Function IsPhantom(ByVal item As PartBomItem) As Boolean
        Return item IsNot Nothing AndAlso Normalize(item.BomStructure) = "PHANTOM"
    End Function

    Public Shared Function IsPurchased(ByVal item As PartBomItem) As Boolean
        Return item IsNot Nothing AndAlso Normalize(item.BomStructure) = "PURCHASED"
    End Function

    Public Shared Function IsInseparable(ByVal item As PartBomItem) As Boolean
        Return item IsNot Nothing AndAlso Normalize(item.BomStructure) = "INSEPARABLE"
    End Function

    Public Shared Function IsEffectiveBomLeaf(ByVal item As PartBomItem) As Boolean
        If item Is Nothing Then Return False
        Dim s As String = Normalize(item.BomStructure)
        Return s = "NORMAL" OrElse s = "PURCHASED" OrElse s = "INSEPARABLE"
    End Function

    Public Shared Function StatusText(ByVal item As PartBomItem) As String
        If item Is Nothing Then Return ""
        Return Normalize(item.BomStructure)
    End Function
End Class


Public Class BomStructureAuditResult
    Public Errors As New List(Of String)()
    Public Warnings As New List(Of String)()
    Public Function IsValid() As Boolean
        Return Errors.Count = 0
    End Function
End Class

Public Class BomStructureAuditEngine
    Public Shared Function Audit(ByVal root As BomAssemblyNode) As BomStructureAuditResult
        Dim result As New BomStructureAuditResult()
        If root Is Nothing Then
            result.Errors.Add("Structure root is Nothing.")
            Return result
        End If
        Dim visited As New HashSet(Of BomAssemblyNode)()
        AuditNode(root, visited, result)
        Return result
    End Function

    Private Shared Sub AuditNode(ByVal node As BomAssemblyNode,
                                 ByVal visited As HashSet(Of BomAssemblyNode),
                                 ByVal result As BomStructureAuditResult)
        If node Is Nothing Then Return
        If visited.Contains(node) Then
            result.Errors.Add("Cycle detected at: " & node.FullPath)
            Return
        End If
        visited.Add(node)

        For Each entry As BomAssemblyPartEntry In node.DirectParts.Values
            If entry Is Nothing OrElse entry.Item Is Nothing Then
                result.Warnings.Add("Empty BOM entry at: " & node.FullPath)
                Continue For
            End If
            If entry.LocalQuantity < 0 Then
                result.Errors.Add("Negative Local Qty: " & entry.Item.FileName)
            End If
            Dim structureName As String = BomStructurePolicy.Normalize(entry.Item.BomStructure)
            If structureName <> "NORMAL" AndAlso structureName <> "PURCHASED" AndAlso
               structureName <> "PHANTOM" AndAlso structureName <> "REFERENCE" AndAlso
               structureName <> "INSEPARABLE" Then
                result.Warnings.Add("Unknown BOM Structure [" & structureName & "]: " & entry.Item.FileName)
            End If
        Next

        For Each child As BomAssemblyNode In node.Children.Values
            If child Is Nothing Then Continue For
            If child.Parent IsNot node Then
                result.Errors.Add("Invalid Parent link: " & child.FullPath)
            End If
            AuditNode(child, visited, result)
        Next
        visited.Remove(node)
    End Sub
End Class

Public Class BomStructureEngine
    Public Shared Function Build(ByVal rootAssemblyName As String, ByVal items As List(Of PartBomItem)) As BomAssemblyNode
        Dim rootName As String = If(String.IsNullOrWhiteSpace(rootAssemblyName), "ROOT", rootAssemblyName)
        Dim root As New BomAssemblyNode(rootName, rootName, 0, Nothing)
        If items Is Nothing Then Return root

        For Each item As PartBomItem In items
            If item Is Nothing Then Continue For
            Dim paths As List(Of String) = item.GetAssemblyPaths()
            If paths.Count = 0 Then
                root.AddDirectPart(item, item.Quantity)
                Continue For
            End If

            For Each rawPath As String In paths
                If String.IsNullOrWhiteSpace(rawPath) Then Continue For
                Dim names() As String = rawPath.Trim().Trim("\"c).Split("\"c)
                Dim current As BomAssemblyNode = root
                Dim builtPath As String = ""
                Dim startIndex As Integer = 0
                If names.Length > 0 AndAlso String.Equals(names(0).Trim(), rootName, StringComparison.OrdinalIgnoreCase) Then startIndex = 1

                For i As Integer = startIndex To names.Length - 1
                    Dim n As String = names(i).Trim()
                    If n.Length = 0 Then Continue For
                    builtPath = If(builtPath.Length = 0, rootName & "\" & n, builtPath & "\" & n)
                    current = current.GetOrCreateChild(n, builtPath)
                Next

                Dim q As Integer = item.GetQuantityForAssemblyPath(rawPath)
                If q <= 0 Then q = item.GetQuantityForParent(current.Name)
                If q <= 0 Then q = item.Quantity
                current.AddDirectPart(item, q)
            Next
        Next
        Return root
    End Function
End Class


'####################################################################
' PHASE 5 - PROJECT INTELLIGENCE
' WHERE USED 2.0 / DEPENDENCY TREE / IMPACT ANALYSIS
'####################################################################
Public Class BomWhereUsedNode
    Public Name As String = ""
    Public FullPath As String = ""
    Public Level As Integer = 0
    Public LocalQty As Integer = 0
    Public TotalQty As Integer = 0
    Public OccurrenceCount As Integer = 0
    Public SuppressedCount As Integer = 0
    Public VisibleCount As Integer = 0
    Public Children As New List(Of BomWhereUsedNode)()
End Class

Public Class BomImpactResult
    Public Part As PartBomItem = Nothing
    Public Assemblies As New HashSet(Of String)(StringComparer.OrdinalIgnoreCase)
    Public AssemblyPaths As New HashSet(Of String)(StringComparer.OrdinalIgnoreCase)
    Public Drawings As New HashSet(Of String)(StringComparer.OrdinalIgnoreCase)
    Public OccurrenceCount As Integer = 0
    Public SuppressedCount As Integer = 0
    Public VisibleCount As Integer = 0
End Class

Public Class BomWhereUsedEngine
    Public Shared Function BuildTree(ByVal item As PartBomItem, ByVal rootAssembly As String) As BomWhereUsedNode
        Dim root As New BomWhereUsedNode()
        root.Name = If(String.IsNullOrWhiteSpace(item.PartNumber), item.FileName, item.PartNumber)
        root.FullPath = root.Name
        root.Level = 0
        If item Is Nothing Then Return root

        Dim paths As List(Of String) = item.GetAssemblyPaths()
        For Each rawPath As String In paths
            If String.IsNullOrWhiteSpace(rawPath) Then Continue For
            Dim names() As String = rawPath.Trim().Trim("\"c).Split("\"c)
            Dim current As BomWhereUsedNode = root
            Dim built As String = ""
            For i As Integer = names.Length - 1 To 0 Step -1
                Dim n As String = names(i).Trim()
                If n.Length = 0 Then Continue For
                built = If(built.Length = 0, n, n & "\" & built)
                Dim child As BomWhereUsedNode = Nothing
                For Each c As BomWhereUsedNode In current.Children
                    If String.Equals(c.Name, n, StringComparison.OrdinalIgnoreCase) Then
                        child = c
                        Exit For
                    End If
                Next
                If child Is Nothing Then
                    child = New BomWhereUsedNode()
                    child.Name = n
                    child.FullPath = built
                    child.Level = current.Level + 1
                    current.Children.Add(child)
                End If
                child.LocalQty += Math.Max(1, item.GetQuantityForAssemblyPath(rawPath))
                child.OccurrenceCount += 1
                current = child
            Next
        Next

        root.TotalQty = Math.Max(0, item.Quantity)
        root.SuppressedCount = Math.Max(0, item.SuppressedCount)
        root.VisibleCount = Math.Max(0, root.TotalQty - root.SuppressedCount)
        Return root
    End Function

    Public Shared Function AnalyzeImpact(ByVal item As PartBomItem,
                                         ByVal drawingIndex As Dictionary(Of String, String)) As BomImpactResult
        Dim result As New BomImpactResult()
        result.Part = item
        If item Is Nothing Then Return result

        result.OccurrenceCount = Math.Max(0, item.Quantity)
        result.SuppressedCount = Math.Max(0, item.SuppressedCount)
        result.VisibleCount = Math.Max(0, result.OccurrenceCount - result.SuppressedCount)

        For Each p As String In item.GetAssemblyPaths()
            If String.IsNullOrWhiteSpace(p) Then Continue For
            result.AssemblyPaths.Add(p)
            Dim names() As String = p.Trim().Trim("\"c).Split("\"c)
            For Each n As String In names
                If Not String.IsNullOrWhiteSpace(n) Then result.Assemblies.Add(n.Trim())
            Next
        Next

        If drawingIndex IsNot Nothing Then
            Dim keys As New List(Of String)()
            If Not String.IsNullOrWhiteSpace(item.FileName) Then keys.Add(System.IO.Path.GetFileNameWithoutExtension(item.FileName))
            If Not String.IsNullOrWhiteSpace(item.PartNumber) Then keys.Add(item.PartNumber)
            For Each k As String In keys
                Dim drawingPath As String = ""
                If drawingIndex.TryGetValue(k, drawingPath) Then
                    If Not String.IsNullOrWhiteSpace(drawingPath) Then result.Drawings.Add(drawingPath)
                End If
            Next
        End If
        Return result
    End Function
End Class



Public Class BomDependencyCacheEntry
    Public Signature As String = ""
    Public Root As BomWhereUsedNode = Nothing
    Public Impact As BomImpactResult = Nothing
End Class

Public Class BomDependencyCache
    Private Shared ReadOnly _entries As New Dictionary(Of String, BomDependencyCacheEntry)(StringComparer.OrdinalIgnoreCase)

    Public Shared Function MakeKey(ByVal item As PartBomItem) As String
        If item Is Nothing Then Return ""
        If Not String.IsNullOrWhiteSpace(item.DocumentKey) Then Return item.DocumentKey
        If Not String.IsNullOrWhiteSpace(item.FilePath) Then Return item.FilePath
        Return item.PartNumber & "|" & item.FileName
    End Function

    Public Shared Function MakeSignature(ByVal item As PartBomItem) As String
        If item Is Nothing Then Return ""
        Dim sb As New System.Text.StringBuilder()
        sb.Append(item.Quantity.ToString()).Append("|")
        sb.Append(item.SuppressedCount.ToString()).Append("|")
        For Each p As String In item.GetAssemblyPaths()
            sb.Append(p).Append(";")
        Next
        Return sb.ToString()
    End Function

    Public Shared Function TryGet(ByVal item As PartBomItem, ByRef root As BomWhereUsedNode, ByRef impact As BomImpactResult) As Boolean
        Dim key As String = MakeKey(item)
        If key.Length = 0 Then Return False
        Dim entry As BomDependencyCacheEntry = Nothing
        If Not _entries.TryGetValue(key, entry) OrElse entry Is Nothing Then Return False
        If Not String.Equals(entry.Signature, MakeSignature(item), StringComparison.Ordinal) Then
            _entries.Remove(key)
            Return False
        End If
        root = entry.Root
        impact = entry.Impact
        Return root IsNot Nothing AndAlso impact IsNot Nothing
    End Function

    Public Shared Sub Put(ByVal item As PartBomItem, ByVal root As BomWhereUsedNode, ByVal impact As BomImpactResult)
        Dim key As String = MakeKey(item)
        If key.Length = 0 Then Exit Sub
        Dim entry As New BomDependencyCacheEntry()
        entry.Signature = MakeSignature(item)
        entry.Root = root
        entry.Impact = impact
        _entries(key) = entry
    End Sub

    Public Shared Sub Invalidate(ByVal item As PartBomItem)
        Dim key As String = MakeKey(item)
        If key.Length > 0 Then _entries.Remove(key)
    End Sub

    Public Shared Sub Clear()
        _entries.Clear()
    End Sub
End Class

Public Class BomDependencyForm
    Inherits Form

    Private _tree As TreeView
    Private _grid As DataGridView
    Private _closeButton As Button
    Private _item As PartBomItem
    Private _impact As BomImpactResult
    Private _root As BomWhereUsedNode
    Private _openDrawing As Action(Of String)
    Private _locateAssembly As Action(Of String)
    Private _filterImpact As Action(Of BomImpactResult)

    Public Sub New(ByVal item As PartBomItem,
                   ByVal root As BomWhereUsedNode,
                   ByVal impact As BomImpactResult,
                   ByVal openDrawing As Action(Of String),
                   ByVal locateAssembly As Action(Of String),
                   ByVal filterImpact As Action(Of BomImpactResult))
        _item = item
        _root = root
        _impact = impact
        _openDrawing = openDrawing
        _locateAssembly = locateAssembly
        _filterImpact = filterImpact

        Text = "PROJECT INTELLIGENCE - WHERE USED / IMPACT"
        StartPosition = FormStartPosition.CenterParent
        Width = 980
        Height = 680
        MinimizeBox = False

        Dim split As New SplitContainer()
        split.Dock = DockStyle.Fill
        split.Orientation = Orientation.Vertical
        split.SplitterDistance = 430

        _tree = New TreeView()
        _tree.Dock = DockStyle.Fill
        _tree.HideSelection = False
        AddHandler _tree.NodeMouseDoubleClick, AddressOf TreeDoubleClick

        _grid = New DataGridView()
        _grid.Dock = DockStyle.Fill
        _grid.ReadOnly = True
        _grid.AllowUserToAddRows = False
        _grid.AllowUserToDeleteRows = False
        _grid.AutoSizeColumnsMode = DataGridViewAutoSizeColumnsMode.Fill
        _grid.SelectionMode = DataGridViewSelectionMode.FullRowSelect
        _grid.Columns.Add("TYPE", "TYPE")
        _grid.Columns.Add("NAME", "NAME / PATH")
        _grid.Columns.Add("DETAIL", "DETAIL")
        AddHandler _grid.CellDoubleClick, AddressOf GridDoubleClick

        split.Panel1.Controls.Add(_tree)
        split.Panel2.Controls.Add(_grid)

        Dim bottom As New Panel()
        bottom.Dock = DockStyle.Bottom
        bottom.Height = 44
        Dim filterButton As New Button()
        filterButton.Text = "FILTER IMPACT"
        filterButton.Width = 125
        filterButton.Height = 28
        filterButton.Left = 705
        filterButton.Top = 8
        filterButton.Anchor = AnchorStyles.Right Or AnchorStyles.Top
        AddHandler filterButton.Click, Sub()
                                           If _filterImpact IsNot Nothing Then _filterImpact(_impact)
                                       End Sub
        bottom.Controls.Add(filterButton)

        _closeButton = New Button()
        _closeButton.Text = "CLOSE"
        _closeButton.Width = 100
        _closeButton.Height = 28
        _closeButton.Left = 840
        _closeButton.Top = 8
        _closeButton.Anchor = AnchorStyles.Right Or AnchorStyles.Top
        AddHandler _closeButton.Click, Sub() Me.Close()
        bottom.Controls.Add(_closeButton)

        Controls.Add(split)
        Controls.Add(bottom)
        BuildContent()
    End Sub

    Private Sub BuildContent()
        _tree.Nodes.Clear()
        _grid.Rows.Clear()

        Dim partName As String = If(_item Is Nothing, "", If(String.IsNullOrWhiteSpace(_item.PartNumber), _item.FileName, _item.PartNumber))
        Dim rootNode As New TreeNode(partName & "   [PART]")
        rootNode.Tag = "PART|" & partName
        _tree.Nodes.Add(rootNode)
        AddWhereUsedChildren(rootNode, _root)

        Dim drawingRoot As New TreeNode("DRAWINGS (" & If(_impact Is Nothing, 0, _impact.Drawings.Count).ToString() & ")")
        drawingRoot.Tag = "GROUP|DRAWINGS"
        rootNode.Nodes.Add(drawingRoot)
        If _impact IsNot Nothing Then
            Dim drawings As New List(Of String)(_impact.Drawings)
            drawings.Sort(StringComparer.OrdinalIgnoreCase)
            For Each d As String In drawings
                Dim dn As New TreeNode(System.IO.Path.GetFileName(d))
                dn.ToolTipText = d
                dn.Tag = "DRAWING|" & d
                drawingRoot.Nodes.Add(dn)
                _grid.Rows.Add("DRAWING", d, "Double-click để mở")
            Next

            Dim paths As New List(Of String)(_impact.AssemblyPaths)
            paths.Sort(StringComparer.OrdinalIgnoreCase)
            For Each p As String In paths
                _grid.Rows.Add("ASSEMBLY PATH", p, "Dependency")
            Next
        End If

        If _item IsNot Nothing Then
            _grid.Rows.Insert(0, "SUMMARY", partName,
                              "Qty=" & _item.Quantity.ToString() &
                              " | Visible=" & Math.Max(0, _item.Quantity - _item.SuppressedCount).ToString() &
                              " | Suppressed=" & Math.Max(0, _item.SuppressedCount).ToString())
        End If

        rootNode.Expand()
        drawingRoot.Expand()
    End Sub

    Private Sub AddWhereUsedChildren(ByVal parentTree As TreeNode, ByVal source As BomWhereUsedNode)
        If source Is Nothing Then Exit Sub
        Dim children As New List(Of BomWhereUsedNode)(source.Children)
        children.Sort(Function(a As BomWhereUsedNode, b As BomWhereUsedNode) StringComparer.OrdinalIgnoreCase.Compare(a.Name, b.Name))
        For Each child As BomWhereUsedNode In children
            Dim relation As String = If(parentTree.Parent Is Nothing, "DIRECT", "INDIRECT")
            Dim label As String = child.Name & "   [" & relation & " | Local " & child.LocalQty.ToString() & " | Occ " & child.OccurrenceCount.ToString() & "]"
            Dim tn As New TreeNode(label)
            tn.Tag = "ASSEMBLY|" & child.Name
            tn.ToolTipText = child.FullPath
            parentTree.Nodes.Add(tn)
            AddWhereUsedChildren(tn, child)
        Next
    End Sub

    Private Sub TreeDoubleClick(ByVal sender As Object, ByVal e As TreeNodeMouseClickEventArgs)
        If e Is Nothing OrElse e.Node Is Nothing OrElse e.Node.Tag Is Nothing Then Exit Sub
        Dim tagText As String = CStr(e.Node.Tag)
        If tagText.StartsWith("DRAWING|", StringComparison.OrdinalIgnoreCase) Then
            Dim p As String = tagText.Substring(8)
            If _openDrawing IsNot Nothing Then _openDrawing(p)
        ElseIf tagText.StartsWith("ASSEMBLY|", StringComparison.OrdinalIgnoreCase) Then
            Dim a As String = tagText.Substring(9)
            If _locateAssembly IsNot Nothing Then _locateAssembly(a)
        End If
    End Sub

    Private Sub GridDoubleClick(ByVal sender As Object, ByVal e As DataGridViewCellEventArgs)
        If e.RowIndex < 0 OrElse e.RowIndex >= _grid.Rows.Count Then Exit Sub
        Dim row As DataGridViewRow = _grid.Rows(e.RowIndex)
        Dim kind As String = Convert.ToString(row.Cells("TYPE").Value)
        Dim value As String = Convert.ToString(row.Cells("NAME").Value)
        If String.Equals(kind, "DRAWING", StringComparison.OrdinalIgnoreCase) Then
            If _openDrawing IsNot Nothing Then _openDrawing(value)
        ElseIf String.Equals(kind, "ASSEMBLY PATH", StringComparison.OrdinalIgnoreCase) Then
            Dim names() As String = value.Trim().Trim("\"c).Split("\"c)
            If names.Length > 0 AndAlso _locateAssembly IsNot Nothing Then _locateAssembly(names(names.Length - 1))
        End If
    End Sub
End Class


'####################################################################
' PHASE 6 - CHANGE MANAGEMENT
' SNAPSHOT / BOM COMPARE / CHANGE SET / CHANGE REPORT
'####################################################################
Public Class BomSnapshotItem
    Public Key As String = ""
    Public FileName As String = ""
    Public FilePath As String = ""
    Public PartNumber As String = ""
    Public Description As String = ""
    Public Material As String = ""
    Public Revision As String = ""
    Public BomStructure As String = ""
    Public Quantity As Integer = 0
End Class

Public Class BomSnapshot
    Public Name As String = ""
    Public CreatedUtc As DateTime = DateTime.UtcNow
    Public AssemblyName As String = ""
    Public Items As New Dictionary(Of String, BomSnapshotItem)(StringComparer.OrdinalIgnoreCase)
End Class

Public Enum BomChangeKind
    Added = 0
    Removed = 1
    QuantityChanged = 2
    PropertyChanged = 3
End Enum

Public Class BomChangeRecord
    Public Kind As BomChangeKind
    Public Key As String = ""
    Public PartNumber As String = ""
    Public FileName As String = ""
    Public FieldName As String = ""
    Public OldValue As String = ""
    Public NewValue As String = ""
End Class

Public Class BomChangeSet
    Public SnapshotName As String = ""
    Public ComparedUtc As DateTime = DateTime.UtcNow
    Public Changes As New List(Of BomChangeRecord)()

    Public Function CountKind(ByVal kind As BomChangeKind) As Integer
        Dim n As Integer = 0
        For Each c As BomChangeRecord In Changes
            If c IsNot Nothing AndAlso c.Kind = kind Then n += 1
        Next
        Return n
    End Function
End Class

Public Class BomChangeManagementEngine
    Public Shared Function Capture(ByVal snapshotName As String,
                                   ByVal assemblyName As String,
                                   ByVal items As List(Of PartBomItem)) As BomSnapshot
        Dim snap As New BomSnapshot()
        snap.Name = snapshotName
        snap.AssemblyName = assemblyName
        snap.CreatedUtc = DateTime.UtcNow
        If items Is Nothing Then Return snap

        For Each item As PartBomItem In items
            If item Is Nothing Then Continue For
            Dim s As New BomSnapshotItem()
            s.Key = MakeKey(item)
            s.FileName = If(item.FileName, "")
            s.FilePath = If(item.FilePath, "")
            s.PartNumber = If(item.PartNumber, "")
            s.Description = If(item.Description, "")
            s.Material = If(item.Material, "")
            s.Revision = If(item.Revision, "")
            s.BomStructure = If(item.BomStructure, "")
            s.Quantity = Math.Max(0, item.Quantity)
            If s.Key.Length > 0 Then snap.Items(s.Key) = s
        Next
        Return snap
    End Function

    Public Shared Function Compare(ByVal snap As BomSnapshot,
                                   ByVal currentItems As List(Of PartBomItem)) As BomChangeSet
        Dim result As New BomChangeSet()
        If snap Is Nothing Then Return result
        result.SnapshotName = snap.Name

        Dim current As New Dictionary(Of String, PartBomItem)(StringComparer.OrdinalIgnoreCase)
        If currentItems IsNot Nothing Then
            For Each item As PartBomItem In currentItems
                If item Is Nothing Then Continue For
                Dim key As String = MakeKey(item)
                If key.Length > 0 Then current(key) = item
            Next
        End If

        For Each pair As KeyValuePair(Of String, BomSnapshotItem) In snap.Items
            Dim oldItem As BomSnapshotItem = pair.Value
            Dim nowItem As PartBomItem = Nothing
            If Not current.TryGetValue(pair.Key, nowItem) Then
                AddChange(result, BomChangeKind.Removed, oldItem, Nothing, "ITEM", oldItem.PartNumber, "")
                Continue For
            End If

            If oldItem.Quantity <> nowItem.Quantity Then
                AddChange(result, BomChangeKind.QuantityChanged, oldItem, nowItem, "QTY",
                          oldItem.Quantity.ToString(), nowItem.Quantity.ToString())
            End If
            CompareField(result, oldItem, nowItem, "PART NUMBER", oldItem.PartNumber, nowItem.PartNumber)
            CompareField(result, oldItem, nowItem, "DESCRIPTION", oldItem.Description, nowItem.Description)
            CompareField(result, oldItem, nowItem, "MATERIAL", oldItem.Material, nowItem.Material)
            CompareField(result, oldItem, nowItem, "REVISION", oldItem.Revision, nowItem.Revision)
            CompareField(result, oldItem, nowItem, "BOM STRUCTURE", oldItem.BomStructure, nowItem.BomStructure)
            current.Remove(pair.Key)
        Next

        For Each pair As KeyValuePair(Of String, PartBomItem) In current
            AddChange(result, BomChangeKind.Added, Nothing, pair.Value, "ITEM", "", pair.Value.PartNumber)
        Next
        Return result
    End Function

    Private Shared Sub CompareField(ByVal result As BomChangeSet,
                                    ByVal oldItem As BomSnapshotItem,
                                    ByVal nowItem As PartBomItem,
                                    ByVal fieldName As String,
                                    ByVal oldValue As String,
                                    ByVal newValue As String)
        If Not String.Equals(If(oldValue, ""), If(newValue, ""), StringComparison.Ordinal) Then
            AddChange(result, BomChangeKind.PropertyChanged, oldItem, nowItem, fieldName, oldValue, newValue)
        End If
    End Sub

    Private Shared Sub AddChange(ByVal result As BomChangeSet,
                                 ByVal kind As BomChangeKind,
                                 ByVal oldItem As BomSnapshotItem,
                                 ByVal nowItem As PartBomItem,
                                 ByVal fieldName As String,
                                 ByVal oldValue As String,
                                 ByVal newValue As String)
        Dim c As New BomChangeRecord()
        c.Kind = kind
        c.Key = If(nowItem IsNot Nothing, MakeKey(nowItem), If(oldItem IsNot Nothing, oldItem.Key, ""))
        c.PartNumber = If(nowItem IsNot Nothing, nowItem.PartNumber, If(oldItem IsNot Nothing, oldItem.PartNumber, ""))
        c.FileName = If(nowItem IsNot Nothing, nowItem.FileName, If(oldItem IsNot Nothing, oldItem.FileName, ""))
        c.FieldName = fieldName
        c.OldValue = If(oldValue, "")
        c.NewValue = If(newValue, "")
        result.Changes.Add(c)
    End Sub

    Public Shared Function MakeKey(ByVal item As PartBomItem) As String
        If item Is Nothing Then Return ""
        If Not String.IsNullOrWhiteSpace(item.DocumentKey) Then Return item.DocumentKey
        If Not String.IsNullOrWhiteSpace(item.FilePath) Then Return item.FilePath
        Return item.PartNumber & "|" & item.FileName
    End Function
End Class

Public Class BomChangeSetForm
    Inherits Form
    Private _grid As DataGridView

    Public Sub New(ByVal changeSet As BomChangeSet)
        Text = "BOM CHANGE SET  | V23 FINAL"
        StartPosition = FormStartPosition.CenterParent
        Width = 1050
        Height = 650

        Dim summary As New Label()
        summary.Dock = DockStyle.Top
        summary.Height = 42
        summary.TextAlign = ContentAlignment.MiddleLeft
        summary.Font = New Font("Segoe UI Semibold", 9.5F)
        summary.Text = "Snapshot: " & changeSet.SnapshotName &
                       "    | ADDED " & changeSet.CountKind(BomChangeKind.Added).ToString() &
                       " | REMOVED " & changeSet.CountKind(BomChangeKind.Removed).ToString() &
                       " | QTY " & changeSet.CountKind(BomChangeKind.QuantityChanged).ToString() &
                       " | PROPERTY " & changeSet.CountKind(BomChangeKind.PropertyChanged).ToString()

        _grid = New DataGridView()
        _grid.Dock = DockStyle.Fill
        _grid.ReadOnly = True
        _grid.AllowUserToAddRows = False
        _grid.AllowUserToDeleteRows = False
        _grid.AutoSizeColumnsMode = DataGridViewAutoSizeColumnsMode.Fill
        _grid.SelectionMode = DataGridViewSelectionMode.FullRowSelect
        _grid.Columns.Add("KIND", "CHANGE")
        _grid.Columns.Add("PN", "PART NUMBER")
        _grid.Columns.Add("FILE", "FILE")
        _grid.Columns.Add("FIELD", "FIELD")
        _grid.Columns.Add("OLD", "OLD VALUE")
        _grid.Columns.Add("NEW", "NEW VALUE")

        For Each c As BomChangeRecord In changeSet.Changes
            _grid.Rows.Add(c.Kind.ToString().ToUpperInvariant(), c.PartNumber, c.FileName, c.FieldName, c.OldValue, c.NewValue)
        Next

        Controls.Add(_grid)
        Controls.Add(summary)
    End Sub
End Class


'####################################################################
' PHASE 7 - MANUFACTURING INTELLIGENCE
' MATERIAL / THICKNESS / PROCESS / PROCUREMENT SUMMARY
'####################################################################
Public Class BomManufacturingGroup
    Public Key As String = ""
    Public Material As String = ""
    Public Thickness As String = ""
    Public ProcessName As String = ""
    Public PartCount As Integer = 0
    Public TotalQty As Integer = 0
    Public PurchasedCount As Integer = 0
    Public ManufacturedCount As Integer = 0
End Class

Public Class BomManufacturingSummary
    Public Groups As New List(Of BomManufacturingGroup)()
    Public TotalUniqueParts As Integer = 0
    Public TotalQty As Integer = 0
    Public PurchasedParts As Integer = 0
    Public ManufacturedParts As Integer = 0
    Public ReferenceParts As Integer = 0
End Class


Public Enum BomManufacturingType
    Unknown = 0
    Plate = 1
    Profile = 2
    Tube = 3
    SheetMetal = 4
    Purchased = 5
    Fastener = 6
End Enum

Public Enum BomClassificationConfidence
    Low = 0
    Medium = 1
    High = 2
    Manual = 3
End Enum

Public Class BomManufacturingRecord
    Public PartNumber As String = ""
    Public Description As String = ""
    Public Material As String = ""
    Public ManufacturingType As BomManufacturingType = BomManufacturingType.Unknown
    Public Confidence As BomClassificationConfidence = BomClassificationConfidence.Low
    Public Thickness As Double = 0
    Public Width As Double = 0
    Public Length As Double = 0
    Public Quantity As Integer = 0
    Public UnitMass As Double = 0
    Public TotalMass As Double = 0
    Public Profile As String = ""
    Public Section As String = ""
    Public Standard As String = ""
    Public Vendor As String = ""
    Public StockNumber As String = ""
    Public ManualOverride As Boolean = False
End Class


Public Class BomManufacturingListBuilder
    Public Shared Function BuildRecords(ByVal items As List(Of PartBomItem)) As List(Of BomManufacturingRecord)
        Dim result As New List(Of BomManufacturingRecord)()
        If items Is Nothing Then Return result
        For Each item As PartBomItem In items
            If item Is Nothing Then Continue For
            Dim r As New BomManufacturingRecord()
            r.PartNumber = item.PartNumber
            r.Description = item.Description
            r.Material = item.Material
            r.Quantity = Math.Max(1, item.Quantity)
            r.UnitMass = item.Mass
            r.TotalMass = r.UnitMass * r.Quantity
            r.Thickness = item.Thickness
            r.Length = item.BoundingMaxMm
            r.Width = item.BoundingMidMm

            Dim pn As String = (If(item.PartNumber, "") & " " & If(item.Description, "")).ToUpperInvariant()
            If item.IsPurchased Then
                r.ManufacturingType = BomManufacturingType.Purchased
                r.Confidence = BomClassificationConfidence.High
            ElseIf pn.Contains("BOLT") OrElse pn.Contains("SCREW") OrElse pn.Contains("NUT") OrElse pn.Contains("WASHER") Then
                r.ManufacturingType = BomManufacturingType.Fastener
                r.Confidence = BomClassificationConfidence.Medium
            ElseIf item.IsSheetMetal Then
                r.ManufacturingType = BomManufacturingType.SheetMetal
                r.Confidence = BomClassificationConfidence.High
            ElseIf r.Thickness > 0 AndAlso item.BoundingMaxMm > 0 AndAlso item.BoundingMinMm > 0 AndAlso
                   r.Thickness <= Math.Max(0.01R, item.BoundingMinMm * 1.25R) Then
                r.ManufacturingType = BomManufacturingType.Plate
                r.Confidence = BomClassificationConfidence.Medium
            ElseIf pn.Contains("PIPE") OrElse pn.Contains("TUBE") OrElse pn.Contains("ỐNG") Then
                r.ManufacturingType = BomManufacturingType.Tube
                r.Confidence = BomClassificationConfidence.Medium
            ElseIf pn.Contains("ANGLE") OrElse pn.Contains("CHANNEL") OrElse pn.Contains("PROFILE") OrElse pn.Contains("I-BEAM") OrElse pn.Contains("H-BEAM") OrElse pn.Contains("C-SECTION") Then
                r.ManufacturingType = BomManufacturingType.Profile
                r.Confidence = BomClassificationConfidence.Low
            Else
                r.ManufacturingType = BomManufacturingType.Unknown
                r.Confidence = BomClassificationConfidence.Low
            End If
            result.Add(r)
        Next
        Return result
    End Function

    Public Shared Function Filter(ByVal records As List(Of BomManufacturingRecord), ByVal manufacturingType As BomManufacturingType) As List(Of BomManufacturingRecord)
        Dim result As New List(Of BomManufacturingRecord)()
        If records Is Nothing Then Return result
        For Each r As BomManufacturingRecord In records
            If r IsNot Nothing AndAlso r.ManufacturingType = manufacturingType Then result.Add(r)
        Next
        Return result
    End Function
End Class

Public Class BomManufacturingEngine
    Public Shared Function Analyze(ByVal items As List(Of PartBomItem)) As BomManufacturingSummary
        Dim result As New BomManufacturingSummary()
        Dim groups As New Dictionary(Of String, BomManufacturingGroup)(StringComparer.OrdinalIgnoreCase)
        If items Is Nothing Then Return result

        For Each item As PartBomItem In items
            If item Is Nothing Then Continue For
            result.TotalUniqueParts += 1
            result.TotalQty += Math.Max(0, item.Quantity)

            Dim structureName As String = BomStructurePolicy.Normalize(item.BomStructure)
            If structureName = "REFERENCE" Then
                result.ReferenceParts += 1
                Continue For
            End If

            Dim purchased As Boolean = (structureName = "PURCHASED")
            If purchased Then
                result.PurchasedParts += 1
            Else
                result.ManufacturedParts += 1
            End If

            Dim material As String = If(String.IsNullOrWhiteSpace(item.Material), "(NO MATERIAL)", item.Material.Trim())
            Dim thickness As String = GetThicknessText(item)
            Dim processName As String = InferProcess(item, purchased)
            Dim key As String = material & "|" & thickness & "|" & processName

            Dim g As BomManufacturingGroup = Nothing
            If Not groups.TryGetValue(key, g) Then
                g = New BomManufacturingGroup()
                g.Key = key
                g.Material = material
                g.Thickness = thickness
                g.ProcessName = processName
                groups.Add(key, g)
            End If
            g.PartCount += 1
            g.TotalQty += Math.Max(0, item.Quantity)
            If purchased Then g.PurchasedCount += 1 Else g.ManufacturedCount += 1
        Next

        result.Groups = New List(Of BomManufacturingGroup)(groups.Values)
        result.Groups.Sort(Function(a As BomManufacturingGroup, b As BomManufacturingGroup)
                               Dim c As Integer = StringComparer.OrdinalIgnoreCase.Compare(a.Material, b.Material)
                               If c <> 0 Then Return c
                               c = StringComparer.OrdinalIgnoreCase.Compare(a.Thickness, b.Thickness)
                               If c <> 0 Then Return c
                               Return StringComparer.OrdinalIgnoreCase.Compare(a.ProcessName, b.ProcessName)
                           End Function)
        Return result
    End Function

    Private Shared Function GetThicknessText(ByVal item As PartBomItem) As String
        If item Is Nothing Then Return ""
        Try
            If String.Equals(item.GeometryLoadState, "LOADED", StringComparison.OrdinalIgnoreCase) AndAlso item.Thickness > 0 Then
                Return item.Thickness.ToString("0.###")
            End If
        Catch
        End Try
        Return "(LAZY)"
    End Function

    Private Shared Function InferProcess(ByVal item As PartBomItem, ByVal purchased As Boolean) As String
        If purchased Then Return "PURCHASE"
        If item Is Nothing Then Return "UNKNOWN"
        Dim g As String = If(item.GeometryType, "").Trim().ToUpperInvariant()
        If g.Contains("SHEET") OrElse g.Contains("PLATE") Then Return "CUT / BEND"
        If g.Contains("TUBE") OrElse g.Contains("PIPE") OrElse g.Contains("PROFILE") Then Return "CUT / FABRICATION"
        If g.Contains("CYL") OrElse g.Contains("ROUND") Then Return "MACHINING"
        If g.Length > 0 Then Return g
        Return "MANUFACTURE"
    End Function
End Class

Public Class BomManufacturingDashboard
    Inherits Form

    Public Sub New(ByVal summary As BomManufacturingSummary)
        Text = "MANUFACTURING INTELLIGENCE"
        StartPosition = FormStartPosition.CenterParent
        Width = 1050
        Height = 680

        Dim top As New Label()
        top.Dock = DockStyle.Top
        top.Height = 46
        top.TextAlign = ContentAlignment.MiddleLeft
        top.Font = New Font("Segoe UI Semibold", 9.5F)
        top.Text = "UNIQUE PARTS " & summary.TotalUniqueParts.ToString() &
                   "   | TOTAL QTY " & summary.TotalQty.ToString() &
                   "   | MANUFACTURE " & summary.ManufacturedParts.ToString() &
                   "   | PURCHASE " & summary.PurchasedParts.ToString() &
                   "   | REFERENCE " & summary.ReferenceParts.ToString()

        Dim grid As New DataGridView()
        grid.Dock = DockStyle.Fill
        grid.ReadOnly = True
        grid.AllowUserToAddRows = False
        grid.AllowUserToDeleteRows = False
        grid.SelectionMode = DataGridViewSelectionMode.FullRowSelect
        grid.AutoSizeColumnsMode = DataGridViewAutoSizeColumnsMode.Fill
        grid.Columns.Add("MATERIAL", "MATERIAL")
        grid.Columns.Add("THICKNESS", "THICKNESS")
        grid.Columns.Add("PROCESS", "PROCESS")
        grid.Columns.Add("PARTS", "UNIQUE PARTS")
        grid.Columns.Add("QTY", "TOTAL QTY")
        grid.Columns.Add("MFG", "MANUFACTURE")
        grid.Columns.Add("BUY", "PURCHASE")

        For Each g As BomManufacturingGroup In summary.Groups
            grid.Rows.Add(g.Material, g.Thickness, g.ProcessName,
                          g.PartCount.ToString(), g.TotalQty.ToString(),
                          g.ManufacturedCount.ToString(), g.PurchasedCount.ToString())
        Next

        Controls.Add(grid)
        Controls.Add(top)
    End Sub
End Class


'####################################################################
' PHASE 8 - EXPORT / REPORTING CENTER
' UNIFIED REPORT MODEL + CSV/HTML REPORTS
'####################################################################
Public Class BomReportRow
    Public Values As New List(Of String)()
End Class

Public Class BomReportTable
    Public Title As String = ""
    Public Headers As New List(Of String)()
    Public Rows As New List(Of BomReportRow)()
End Class

Public Class BomReportingEngine
    Public Shared Function BuildBomReport(ByVal assemblyName As String,
                                          ByVal items As List(Of PartBomItem)) As BomReportTable
        Dim t As New BomReportTable()
        t.Title = "BOM REPORT - " & assemblyName
        t.Headers.AddRange(New String() {"PART NUMBER","DESCRIPTION","FILE","QTY","MATERIAL","REVISION","BOM STRUCTURE","STATUS"})
        If items Is Nothing Then Return t
        For Each item As PartBomItem In items
            If item Is Nothing Then Continue For
            Dim r As New BomReportRow()
            r.Values.Add(If(item.PartNumber, ""))
            r.Values.Add(If(item.Description, ""))
            r.Values.Add(If(item.FileName, ""))
            r.Values.Add(item.Quantity.ToString())
            r.Values.Add(If(item.Material, ""))
            r.Values.Add(If(item.Revision, ""))
            r.Values.Add(BomStructurePolicy.Normalize(item.BomStructure))
            r.Values.Add(If(item.DataStatus, ""))
            t.Rows.Add(r)
        Next
        Return t
    End Function

    Public Shared Sub ExportCsv(ByVal table As BomReportTable, ByVal fileName As String)
        Using sw As New System.IO.StreamWriter(fileName, False, System.Text.Encoding.UTF8)
            sw.WriteLine(String.Join(",", table.Headers.ConvertAll(Function(x As String) Csv(x)).ToArray()))
            For Each row As BomReportRow In table.Rows
                sw.WriteLine(String.Join(",", row.Values.ConvertAll(Function(x As String) Csv(x)).ToArray()))
            Next
        End Using
    End Sub

    Public Shared Sub ExportHtml(ByVal table As BomReportTable, ByVal fileName As String)
        Dim sb As New System.Text.StringBuilder()
        sb.AppendLine("<!DOCTYPE html><html><head><meta charset=""utf-8""><title>" & H(table.Title) & "</title>")
        sb.AppendLine("<style>body{font-family:Segoe UI,Arial;margin:24px;color:#222}h1{font-size:22px}table{border-collapse:collapse;width:100%;font-size:12px}th,td{border:1px solid #ccc;padding:6px 8px;text-align:left}th{background:#eee;position:sticky;top:0}.summary{margin-bottom:14px}</style></head><body>")
        sb.AppendLine("<h1>" & H(table.Title) & "</h1>")
        sb.AppendLine("<div class=""summary"">Rows: " & table.Rows.Count.ToString() & " | Generated: " & DateTime.Now.ToString("yyyy-MM-dd HH:mm:ss") & "</div>")
        sb.AppendLine("<table><thead><tr>")
        For Each hText As String In table.Headers
            sb.Append("<th>").Append(H(hText)).AppendLine("</th>")
        Next
        sb.AppendLine("</tr></thead><tbody>")
        For Each row As BomReportRow In table.Rows
            sb.AppendLine("<tr>")
            For Each v As String In row.Values
                sb.Append("<td>").Append(H(v)).AppendLine("</td>")
            Next
            sb.AppendLine("</tr>")
        Next
        sb.AppendLine("</tbody></table></body></html>")
        System.IO.File.WriteAllText(fileName, sb.ToString(), System.Text.Encoding.UTF8)
    End Sub

    Private Shared Function Csv(ByVal value As String) As String
        Dim s As String = If(value, "")
        Return """" & s.Replace("""", """""") & """"
    End Function

    Private Shared Function H(ByVal value As String) As String
        Dim s As String = If(value, "")
        Return s.Replace("&","&amp;").Replace("<","&lt;").Replace(">","&gt;").Replace("""","&quot;")
    End Function
End Class

Public Class BomReportCenterForm
    Inherits Form
    Private _grid As DataGridView
    Private _table As BomReportTable

    Public Sub New(ByVal table As BomReportTable)
        _table = table
        Text = "REPORT CENTER"
        StartPosition = FormStartPosition.CenterParent
        Width = 1120
        Height = 700

        Dim top As New Panel()
        top.Dock = DockStyle.Top
        top.Height = 48

        Dim titleLabel As New Label()
        titleLabel.Text = table.Title & "   |   " & table.Rows.Count.ToString() & " ROWS"
        titleLabel.AutoSize = True
        titleLabel.Left = 12
        titleLabel.Top = 15
        titleLabel.Font = New Font("Segoe UI Semibold", 9.5F)
        top.Controls.Add(titleLabel)

        _grid = New DataGridView()
        _grid.Dock = DockStyle.Fill
        _grid.ReadOnly = True
        _grid.AllowUserToAddRows = False
        _grid.AllowUserToDeleteRows = False
        _grid.AutoSizeColumnsMode = DataGridViewAutoSizeColumnsMode.Fill
        _grid.SelectionMode = DataGridViewSelectionMode.FullRowSelect
        For Each h As String In table.Headers
            _grid.Columns.Add("C" & _grid.Columns.Count.ToString(), h)
        Next
        For Each r As BomReportRow In table.Rows
            _grid.Rows.Add(r.Values.ToArray())
        Next

        Controls.Add(_grid)
        Controls.Add(top)
    End Sub
End Class


'####################################################################
' PHASE 9 - UI / UX / PRODUCTIVITY
' COMMAND PALETTE + QUICK FILTERS + KEYBOARD WORKFLOW
'####################################################################
Public Class BomCommandItem
    Public Name As String = ""
    Public Category As String = ""
    Public Description As String = ""
    Public ExecuteAction As Action = Nothing
    Public Overrides Function ToString() As String
        Return Name
    End Function
End Class

Public Class BomCommandPaletteForm
    Inherits Form

    Private _search As System.Windows.Forms.TextBox
    Private _list As ListBox
    Private _description As Label
    Private _all As List(Of BomCommandItem)

    Public Sub New(ByVal commands As List(Of BomCommandItem))
        _all = If(commands, New List(Of BomCommandItem)())
        Text = "COMMAND PALETTE"
        StartPosition = FormStartPosition.CenterParent
        Width = 650
        Height = 500
        MinimizeBox = False
        MaximizeBox = False
        KeyPreview = True

        _search = New System.Windows.Forms.TextBox()
        _search.Dock = DockStyle.Top
        _search.Height = 32
        _search.Font = New Font("Segoe UI", 11.0F)
        AddHandler _search.TextChanged, AddressOf RefreshList
        AddHandler _search.KeyDown, AddressOf SearchKeyDown

        _description = New Label()
        _description.Dock = DockStyle.Bottom
        _description.Height = 54
        _description.Padding = New Padding(8)
        _description.AutoEllipsis = True

        _list = New ListBox()
        _list.Dock = DockStyle.Fill
        _list.Font = New Font("Segoe UI", 10.0F)
        AddHandler _list.SelectedIndexChanged, AddressOf SelectionChanged
        AddHandler _list.DoubleClick, AddressOf ExecuteSelected
        AddHandler _list.KeyDown, AddressOf ListKeyDown

        Controls.Add(_list)
        Controls.Add(_description)
        Controls.Add(_search)

        RefreshList(Nothing, EventArgs.Empty)
        AddHandler Me.Shown, Sub(sender As Object, e As EventArgs) _search.Focus()
    End Sub

    Private Sub RefreshList(ByVal sender As Object, ByVal e As EventArgs)
        Dim q As String = _search.Text.Trim()
        _list.BeginUpdate()
        _list.Items.Clear()
        For Each cmd As BomCommandItem In _all
            If cmd Is Nothing Then Continue For
            If q.Length = 0 OrElse cmd.Name.IndexOf(q, StringComparison.OrdinalIgnoreCase) >= 0 OrElse
               cmd.Category.IndexOf(q, StringComparison.OrdinalIgnoreCase) >= 0 OrElse
               cmd.Description.IndexOf(q, StringComparison.OrdinalIgnoreCase) >= 0 Then
                _list.Items.Add(cmd)
            End If
        Next
        _list.EndUpdate()
        If _list.Items.Count > 0 Then _list.SelectedIndex = 0
    End Sub

    Private Sub SelectionChanged(ByVal sender As Object, ByVal e As EventArgs)
        Dim cmd As BomCommandItem = TryCast(_list.SelectedItem, BomCommandItem)
        If cmd Is Nothing Then
            _description.Text = ""
        Else
            _description.Text = cmd.Category & "  •  " & cmd.Description
        End If
    End Sub

    Private Sub SearchKeyDown(ByVal sender As Object, ByVal e As KeyEventArgs)
        If e.KeyCode = Keys.Down AndAlso _list.Items.Count > 0 Then
            _list.Focus()
            _list.SelectedIndex = Math.Max(0, _list.SelectedIndex)
            e.Handled = True
        ElseIf e.KeyCode = Keys.Enter Then
            ExecuteSelected(Nothing, EventArgs.Empty)
            e.Handled = True
        ElseIf e.KeyCode = Keys.Escape Then
            Close()
        End If
    End Sub

    Private Sub ListKeyDown(ByVal sender As Object, ByVal e As KeyEventArgs)
        If e.KeyCode = Keys.Enter Then
            ExecuteSelected(Nothing, EventArgs.Empty)
            e.Handled = True
        ElseIf e.KeyCode = Keys.Escape Then
            Close()
        End If
    End Sub

    Private Sub ExecuteSelected(ByVal sender As Object, ByVal e As EventArgs)
        Dim cmd As BomCommandItem = TryCast(_list.SelectedItem, BomCommandItem)
        If cmd Is Nothing OrElse cmd.ExecuteAction Is Nothing Then Exit Sub
        Close()
        cmd.ExecuteAction.Invoke()
    End Sub
End Class


'####################################################################
' PHASE 10 - PRODUCTION HARDENING
' SAFE EXECUTION / RECOVERY / CACHE INTEGRITY / DIAGNOSTICS
'####################################################################
Public Class BomProductionDiagnostics
    Public Shared LastOperation As String = ""
    Public Shared LastError As String = ""
    Public Shared ErrorCount As Integer = 0
    Public Shared RecoveryCount As Integer = 0
    Public Shared LastOperationMs As Long = 0

    Public Shared Sub RecordSuccess(ByVal operationName As String, ByVal elapsedMs As Long)
        LastOperation = operationName
        LastOperationMs = elapsedMs
        LastError = ""
    End Sub

    Public Shared Sub RecordFailure(ByVal operationName As String, ByVal ex As Exception, ByVal elapsedMs As Long)
        LastOperation = operationName
        LastOperationMs = elapsedMs
        LastError = If(ex Is Nothing, "Unknown error", ex.Message)
        ErrorCount += 1
    End Sub
End Class

Public Class BomSafeExecution
    Public Shared Function Run(ByVal operationName As String,
                               ByVal action As Action,
                               Optional ByVal showError As Boolean = True) As Boolean
        Dim sw As Stopwatch = Stopwatch.StartNew()
        Try
            If action Is Nothing Then Return False
            action.Invoke()
            sw.Stop()
            BomProductionDiagnostics.RecordSuccess(operationName, sw.ElapsedMilliseconds)
            Return True
        Catch ex As Exception
            sw.Stop()
            BomProductionDiagnostics.RecordFailure(operationName, ex, sw.ElapsedMilliseconds)
            Try
                BomLogger.Log("PRODUCTION", operationName, "SafeExecution", "ERROR", ex.ToString())
            Catch
            End Try
            If showError Then
                MessageBox.Show("Thao tác không hoàn tất:" & System.Environment.NewLine &
                                operationName & System.Environment.NewLine & System.Environment.NewLine &
                                ex.Message,
                                "BOM TOOL - SAFE RECOVERY",
                                MessageBoxButtons.OK, MessageBoxIcon.Error)
            End If
            Return False
        End Try
    End Function
End Class

Public Class BomIntegrityResult
    Public Errors As New List(Of String)()
    Public Warnings As New List(Of String)()
    Public Function IsHealthy() As Boolean
        Return Errors.Count = 0
    End Function
End Class

Public Class BomIntegrityEngine
    Public Shared Function Check(ByVal items As List(Of PartBomItem),
                                 ByVal structureRoot As BomAssemblyNode) As BomIntegrityResult
        Dim result As New BomIntegrityResult()
        Dim keys As New HashSet(Of String)(StringComparer.OrdinalIgnoreCase)

        If items Is Nothing Then
            result.Errors.Add("BOM item cache is Nothing.")
            Return result
        End If

        For Each item As PartBomItem In items
            If item Is Nothing Then
                result.Warnings.Add("Null PartBomItem found.")
                Continue For
            End If
            Dim key As String = BomDependencyCache.MakeKey(item)
            If String.IsNullOrWhiteSpace(key) Then
                result.Warnings.Add("Part without stable key: " & item.FileName)
            ElseIf keys.Contains(key) Then
                result.Warnings.Add("Duplicate cache key: " & key)
            Else
                keys.Add(key)
            End If
            If item.Quantity < 0 Then result.Errors.Add("Negative quantity: " & item.FileName)
        Next

        If structureRoot IsNot Nothing Then
            Dim audit As BomStructureAuditResult = BomStructureAuditEngine.Audit(structureRoot)
            result.Errors.AddRange(audit.Errors)
            result.Warnings.AddRange(audit.Warnings)
        End If
        Return result
    End Function
End Class


'####################################################################
' V23 FINAL - PRODUCTION RELEASE
' FINAL REGRESSION / SYSTEM STATUS / RELEASE BASELINE
'####################################################################
Public Class BomReleaseInfo
    Public Const Version As String = BomConstants.ToolVersion
    Public Const ReleaseName As String = "PRODUCTION HARDENED RELEASE"
    Public Const Architecture As String = "Session + Safety + Performance + Transaction + Validation + Structured BOM + Change + Manufacturing 2.0 + Professional UI"
End Class

Public Class BomRegressionCheck
    Public Name As String = ""
    Public Passed As Boolean = False
    Public Detail As String = ""
End Class

Public Class BomRegressionEngine
    Public Shared Function Run(ByVal items As List(Of PartBomItem),
                               ByVal structureRoot As BomAssemblyNode,
                               ByVal activeSnapshot As BomSnapshot) As List(Of BomRegressionCheck)
        Dim checks As New List(Of BomRegressionCheck)()

        AddCheck(checks, "BOM CACHE", items IsNot Nothing,
                 If(items Is Nothing, "Cache is Nothing", items.Count.ToString() & " items"))

        Dim integrity As BomIntegrityResult = BomIntegrityEngine.Check(items, structureRoot)
        AddCheck(checks, "CACHE / STRUCTURE INTEGRITY", integrity.Errors.Count = 0,
                 "Errors=" & integrity.Errors.Count.ToString() & " Warnings=" & integrity.Warnings.Count.ToString())

        Dim negativeQty As Integer = 0
        Dim duplicateKeys As Integer = 0
        Dim keys As New HashSet(Of String)(StringComparer.OrdinalIgnoreCase)
        If items IsNot Nothing Then
            For Each item As PartBomItem In items
                If item Is Nothing Then Continue For
                If item.Quantity < 0 Then negativeQty += 1
                Dim k As String = BomDependencyCache.MakeKey(item)
                If k.Length > 0 AndAlso Not keys.Add(k) Then duplicateKeys += 1
            Next
        End If
        AddCheck(checks, "QUANTITY ENGINE", negativeQty = 0, "Negative Qty=" & negativeQty.ToString())
        AddCheck(checks, "DOCUMENT IDENTITY", duplicateKeys = 0, "Duplicate Keys=" & duplicateKeys.ToString())

        Dim reportingOk As Boolean = False
        Try
            Dim report As BomReportTable = BomReportingEngine.BuildBomReport("REGRESSION", items)
            reportingOk = (report IsNot Nothing AndAlso report.Headers.Count > 0)
        Catch
            reportingOk = False
        End Try
        AddCheck(checks, "REPORTING ENGINE", reportingOk, If(reportingOk, "Ready", "Failed"))

        Dim mfgOk As Boolean = False
        Try
            Dim mfg As BomManufacturingSummary = BomManufacturingEngine.Analyze(items)
            mfgOk = (mfg IsNot Nothing)
        Catch
            mfgOk = False
        End Try
        AddCheck(checks, "MANUFACTURING ENGINE", mfgOk, If(mfgOk, "Ready", "Failed"))

        AddCheck(checks, "TRANSACTION SAFETY", True, "Staging/Review/Commit/Rollback architecture enabled")
        AddCheck(checks, "VALIDATION ENGINE", True, "Rule-based validation enabled")
        AddCheck(checks, "DEPENDENCY ENGINE", True, "Where Used / Impact cache enabled")
        AddCheck(checks, "CHANGE MANAGEMENT", True,
                 If(activeSnapshot Is Nothing, "Ready - no active snapshot", "Active snapshot: " & activeSnapshot.Name))
        Return checks
    End Function

    Private Shared Sub AddCheck(ByVal checks As List(Of BomRegressionCheck),
                                ByVal name As String,
                                ByVal passed As Boolean,
                                ByVal detail As String)
        Dim c As New BomRegressionCheck()
        c.Name = name
        c.Passed = passed
        c.Detail = detail
        checks.Add(c)
    End Sub
End Class

Public Class PropertyColumnInfo
    Public Key As String
    Public PropertySetDisplayName As String
    Public PropertySetInternalName As String
    Public PropertyName As String
    Public DisplayText As String
    Public DefaultSelected As Boolean
    'True khi cột được tạo trực tiếp trong BOM nhưng iProperty chưa nhất thiết tồn tại trong Part.
    Public IsVirtualCustom As Boolean = False

    'UNIVERSAL CONTROL: cột không phải iProperty mà là thiết lập native của Document/Sheet Metal.
    Public IsSystemSetting As Boolean = False
    Public SettingId As String = ""

    Public Overrides Function ToString() As String
        Return DisplayText
    End Function
End Class

'====================================================================
' FORM CHỌN CỘT
'====================================================================

'####################################################################
' SECTION 11 - PROPERTY SELECTION UI
' Form chọn iProperty, tìm kiếm, sắp xếp và xác nhận cột.
'####################################################################

Public Class BomPropertySelectionForm
    Inherits Form

    Private AvailableList As CheckedListBox
    Private SelectedList As ListBox
    Private AddButton As Button
    Private RemoveButton As Button
    Private MoveUpButton As Button
    Private MoveDownButton As Button
    Private SelectDefaultButton As Button
    Private SelectAllButton As Button
    Private ClearAllButton As Button
    Private ExportButton As Button
    Private CancelFormButton As Button
    Private FileNameCheckBox As CheckBox
    Private FilePathCheckBox As CheckBox
    Private ParentAssemblyCheckBox As CheckBox
    Private OpenExcelCheckBox As CheckBox
    Private SearchTextBox As TextBox
    Private PropertyCountLabel As Label
    Private PartCountLabel As Label
    Private ScanModeBox As ComboBox
    Private ScanModeInfoLabel As Label
    Private AllProperties As List(Of PropertyColumnInfo)

    Public SelectedProperties As New List(Of PropertyColumnInfo)
    Public IncludeFileName As Boolean
    Public IncludeFilePath As Boolean
    Public IncludeParentAssembly As Boolean
    Public OpenExcelAfterExport As Boolean
    Public SelectedScanMode As BomScanMode = BomScanMode.Normal

    Private TotalPartCount As Integer

    Public Sub New( _
        ByVal properties As List(Of PropertyColumnInfo), _
        ByVal partCount As Integer)

        AllProperties = properties
        TotalPartCount = partCount
        InitializeForm()
        LoadProperties("")
        SelectDefaultProperties()
    End Sub

    Private Sub InitializeForm()
        Me.Text = "BOM TOOL PRO - CHỌN CỘT"
        Me.StartPosition = FormStartPosition.CenterScreen
        Me.Size = New Size(1000, 720)
        Me.MinimumSize = New Size(900, 650)
        Me.MaximizeBox = True
        Me.MinimizeBox = False
        Me.Font = New Font("Segoe UI", 9.0F)
        Me.BackColor = Color.FromArgb(245, 247, 250)

        Dim titleLabel As New Label()
        titleLabel.Text = "CHỌN THÔNG TIN XUẤT RA EXCEL"
        titleLabel.Font = New Font("Segoe UI", 15.0F, FontStyle.Bold)
        titleLabel.ForeColor = Color.FromArgb(31, 78, 121)
        titleLabel.AutoSize = True
        titleLabel.Location = New Point(24, 18)
        Me.Controls.Add(titleLabel)

        PartCountLabel = New Label()
        PartCountLabel.Text = _
            "Đã tìm thấy " & TotalPartCount.ToString() & " loại Part."
        PartCountLabel.AutoSize = True
        PartCountLabel.ForeColor = Color.DimGray
        PartCountLabel.Location = New Point(27, 52)
        Me.Controls.Add(PartCountLabel)

        Dim searchLabel As New Label()
        searchLabel.Text = "Tìm iProperty:"
        searchLabel.AutoSize = True
        searchLabel.Location = New Point(24, 88)
        Me.Controls.Add(searchLabel)

        SearchTextBox = New TextBox()
        SearchTextBox.Location = New Point(122, 84)
        SearchTextBox.Size = New Size(360, 25)
        AddHandler SearchTextBox.TextChanged, AddressOf SearchTextChanged
        Me.Controls.Add(SearchTextBox)

        PropertyCountLabel = New Label()
        PropertyCountLabel.AutoSize = True
        PropertyCountLabel.ForeColor = Color.DimGray
        PropertyCountLabel.Location = New Point(500, 88)
        Me.Controls.Add(PropertyCountLabel)

        Dim availableLabel As New Label()
        availableLabel.Text = "iProperty tìm thấy trong các Part"
        availableLabel.Font = New Font("Segoe UI", 9.0F, FontStyle.Bold)
        availableLabel.AutoSize = True
        availableLabel.Location = New Point(24, 125)
        Me.Controls.Add(availableLabel)

        Dim selectedLabel As New Label()
        selectedLabel.Text = "Các cột sẽ xuất — theo đúng thứ tự dưới đây"
        selectedLabel.Font = New Font("Segoe UI", 9.0F, FontStyle.Bold)
        selectedLabel.AutoSize = True
        selectedLabel.Location = New Point(546, 125)
        Me.Controls.Add(selectedLabel)

        AvailableList = New CheckedListBox()
        AvailableList.Location = New Point(24, 150)
        AvailableList.Size = New Size(458, 325)
        AvailableList.CheckOnClick = True
        AvailableList.HorizontalScrollbar = True
        AvailableList.IntegralHeight = False
        AvailableList.BackColor = Color.White
        AddHandler AvailableList.DoubleClick, AddressOf AddSelectedProperties
        Me.Controls.Add(AvailableList)

        SelectedList = New ListBox()
        SelectedList.Location = New Point(546, 150)
        SelectedList.Size = New Size(405, 325)
        SelectedList.HorizontalScrollbar = True
        SelectedList.IntegralHeight = False
        SelectedList.SelectionMode = SelectionMode.One
        SelectedList.BackColor = Color.White
        AddHandler SelectedList.DoubleClick, AddressOf RemoveSelectedProperties
        Me.Controls.Add(SelectedList)

        AddButton = New Button()
        AddButton.Text = "THÊM >"
        AddButton.Location = New Point(488, 218)
        AddButton.Size = New Size(52, 34)
        AddHandler AddButton.Click, AddressOf AddSelectedProperties
        Me.Controls.Add(AddButton)

        RemoveButton = New Button()
        RemoveButton.Text = "< XÓA"
        RemoveButton.Location = New Point(488, 260)
        RemoveButton.Size = New Size(52, 34)
        AddHandler RemoveButton.Click, AddressOf RemoveSelectedProperties
        Me.Controls.Add(RemoveButton)

        MoveUpButton = New Button()
        MoveUpButton.Text = "LÊN"
        MoveUpButton.Location = New Point(854, 484)
        MoveUpButton.Size = New Size(97, 32)
        AddHandler MoveUpButton.Click, AddressOf MoveSelectedPropertyUp
        Me.Controls.Add(MoveUpButton)

        MoveDownButton = New Button()
        MoveDownButton.Text = "XUỐNG"
        MoveDownButton.Location = New Point(748, 484)
        MoveDownButton.Size = New Size(97, 32)
        AddHandler MoveDownButton.Click, AddressOf MoveSelectedPropertyDown
        Me.Controls.Add(MoveDownButton)

        SelectDefaultButton = New Button()
        SelectDefaultButton.Text = "CỘT CƠ BẢN"
        SelectDefaultButton.Location = New Point(24, 484)
        SelectDefaultButton.Size = New Size(112, 32)
        AddHandler SelectDefaultButton.Click, AddressOf SelectDefaultButtonClick
        Me.Controls.Add(SelectDefaultButton)

        SelectAllButton = New Button()
        SelectAllButton.Text = "CHỌN TẤT CẢ"
        SelectAllButton.Location = New Point(144, 484)
        SelectAllButton.Size = New Size(112, 32)
        AddHandler SelectAllButton.Click, AddressOf SelectAllButtonClick
        Me.Controls.Add(SelectAllButton)

        ClearAllButton = New Button()
        ClearAllButton.Text = "BỎ CHỌN"
        ClearAllButton.Location = New Point(264, 484)
        ClearAllButton.Size = New Size(112, 32)
        AddHandler ClearAllButton.Click, AddressOf ClearAllButtonClick
        Me.Controls.Add(ClearAllButton)

        Dim optionsGroup As New GroupBox()
        optionsGroup.Text = "Cột và tùy chọn bổ sung"
        optionsGroup.Location = New Point(24, 530)
        optionsGroup.Size = New Size(927, 92)
        Me.Controls.Add(optionsGroup)

        FileNameCheckBox = New CheckBox()
        FileNameCheckBox.Text = "Tên file"
        FileNameCheckBox.AutoSize = True
        FileNameCheckBox.Checked = True
        FileNameCheckBox.Location = New Point(18, 28)
        optionsGroup.Controls.Add(FileNameCheckBox)

        FilePathCheckBox = New CheckBox()
        FilePathCheckBox.Text = "Đường dẫn file"
        FilePathCheckBox.AutoSize = True
        FilePathCheckBox.Checked = False
        FilePathCheckBox.Location = New Point(120, 28)
        optionsGroup.Controls.Add(FilePathCheckBox)

        ParentAssemblyCheckBox = New CheckBox()
        ParentAssemblyCheckBox.Text = "Nằm trong Assembly"
        ParentAssemblyCheckBox.AutoSize = True
        ParentAssemblyCheckBox.Checked = True
        ParentAssemblyCheckBox.Location = New Point(265, 28)
        optionsGroup.Controls.Add(ParentAssemblyCheckBox)

        OpenExcelCheckBox = New CheckBox()
        OpenExcelCheckBox.Text = "Mở Excel sau khi xuất"
        OpenExcelCheckBox.AutoSize = True
        OpenExcelCheckBox.Checked = True
        OpenExcelCheckBox.Location = New Point(465, 28)
        optionsGroup.Controls.Add(OpenExcelCheckBox)

        Dim scanModeLabel As New Label()
        scanModeLabel.Text = "SCAN MODE:"
        scanModeLabel.AutoSize = True
        scanModeLabel.Font = New Font("Segoe UI", 8.5F, FontStyle.Bold)
        scanModeLabel.Location = New Point(18, 58)
        optionsGroup.Controls.Add(scanModeLabel)

        ScanModeBox = New ComboBox()
        ScanModeBox.DropDownStyle = ComboBoxStyle.DropDownList
        ScanModeBox.Items.AddRange(New Object() {"FAST", "NORMAL", "DEEP"})
        ScanModeBox.SelectedIndex = 1
        ScanModeBox.Location = New Point(105, 54)
        ScanModeBox.Size = New Size(115, 25)
        AddHandler ScanModeBox.SelectedIndexChanged, AddressOf ScanModeChanged
        optionsGroup.Controls.Add(ScanModeBox)

        ScanModeInfoLabel = New Label()
        ScanModeInfoLabel.Text = "NORMAL: Core + Drawing cơ bản, Geometry vẫn Lazy."
        ScanModeInfoLabel.AutoSize = True
        ScanModeInfoLabel.ForeColor = Color.DimGray
        ScanModeInfoLabel.Location = New Point(238, 58)
        optionsGroup.Controls.Add(ScanModeInfoLabel)

        ExportButton = New Button()
        ExportButton.Text = "XUẤT EXCEL"
        ExportButton.Font = New Font("Segoe UI", 10.0F, FontStyle.Bold)
        ExportButton.BackColor = Color.FromArgb(31, 78, 121)
        ExportButton.ForeColor = Color.White
        ExportButton.FlatStyle = FlatStyle.Flat
        ExportButton.Location = New Point(726, 635)
        ExportButton.Size = New Size(145, 38)
        AddHandler ExportButton.Click, AddressOf ExportButtonClick
        Me.Controls.Add(ExportButton)

        CancelFormButton = New Button()
        CancelFormButton.Text = "HỦY"
        CancelFormButton.Location = New Point(879, 635)
        CancelFormButton.Size = New Size(72, 38)
        AddHandler CancelFormButton.Click, AddressOf CancelButtonClick
        Me.Controls.Add(CancelFormButton)

        Me.AcceptButton = ExportButton
        Me.CancelButton = CancelFormButton
    End Sub

    Private Sub LoadProperties(ByVal filterText As String)
        AvailableList.Items.Clear()
        Dim normalizedFilter As String = filterText.Trim()

        For Each propertyInfo As PropertyColumnInfo In AllProperties
            If normalizedFilter.Length > 0 Then
                If propertyInfo.DisplayText.IndexOf( _
                    normalizedFilter, _
                    StringComparison.OrdinalIgnoreCase) < 0 Then
                    Continue For
                End If
            End If

            Dim alreadySelected As Boolean = _
                IsPropertyInSelectedList(propertyInfo.Key)

            AvailableList.Items.Add(propertyInfo, alreadySelected)
        Next

        PropertyCountLabel.Text = _
            AvailableList.Items.Count.ToString() & " iProperty"
    End Sub

    Private Sub SelectDefaultProperties()
        SelectedList.Items.Clear()

        For Each propertyInfo As PropertyColumnInfo In AllProperties
            If propertyInfo.DefaultSelected Then
                SelectedList.Items.Add(propertyInfo)
            End If
        Next

        RefreshAvailableChecks()
    End Sub

    Private Sub SearchTextChanged( _
        ByVal sender As Object, _
        ByVal e As EventArgs)

        LoadProperties(SearchTextBox.Text)
    End Sub

    Private Sub AddSelectedProperties( _
        ByVal sender As Object, _
        ByVal e As EventArgs)

        Dim propertiesToAdd As New List(Of PropertyColumnInfo)

        For index As Integer = 0 To AvailableList.Items.Count - 1
            If AvailableList.GetItemChecked(index) Then
                Dim propertyInfo As PropertyColumnInfo = _
                    CType(AvailableList.Items(index), PropertyColumnInfo)

                If Not IsPropertyInSelectedList(propertyInfo.Key) Then
                    propertiesToAdd.Add(propertyInfo)
                End If
            End If
        Next

        If propertiesToAdd.Count = 0 AndAlso _
           AvailableList.SelectedItem IsNot Nothing Then

            Dim selectedProperty As PropertyColumnInfo = _
                CType(AvailableList.SelectedItem, PropertyColumnInfo)

            If Not IsPropertyInSelectedList(selectedProperty.Key) Then
                propertiesToAdd.Add(selectedProperty)
            End If
        End If

        For Each propertyInfo As PropertyColumnInfo In propertiesToAdd
            SelectedList.Items.Add(propertyInfo)
        Next

        RefreshAvailableChecks()
    End Sub

    Private Sub RemoveSelectedProperties( _
        ByVal sender As Object, _
        ByVal e As EventArgs)

        If SelectedList.SelectedIndex < 0 Then Exit Sub

        Dim selectedIndex As Integer = SelectedList.SelectedIndex
        SelectedList.Items.RemoveAt(selectedIndex)

        If SelectedList.Items.Count > 0 Then
            If selectedIndex >= SelectedList.Items.Count Then
                selectedIndex = SelectedList.Items.Count - 1
            End If

            SelectedList.SelectedIndex = selectedIndex
        End If

        RefreshAvailableChecks()
    End Sub

    Private Sub MoveSelectedPropertyUp( _
        ByVal sender As Object, _
        ByVal e As EventArgs)

        Dim selectedIndex As Integer = SelectedList.SelectedIndex
        If selectedIndex <= 0 Then Exit Sub

        Dim selectedObject As Object = SelectedList.Items(selectedIndex)
        SelectedList.Items.RemoveAt(selectedIndex)
        SelectedList.Items.Insert(selectedIndex - 1, selectedObject)
        SelectedList.SelectedIndex = selectedIndex - 1
    End Sub

    Private Sub MoveSelectedPropertyDown( _
        ByVal sender As Object, _
        ByVal e As EventArgs)

        Dim selectedIndex As Integer = SelectedList.SelectedIndex

        If selectedIndex < 0 OrElse _
           selectedIndex >= SelectedList.Items.Count - 1 Then
            Exit Sub
        End If

        Dim selectedObject As Object = SelectedList.Items(selectedIndex)
        SelectedList.Items.RemoveAt(selectedIndex)
        SelectedList.Items.Insert(selectedIndex + 1, selectedObject)
        SelectedList.SelectedIndex = selectedIndex + 1
    End Sub

    Private Sub SelectDefaultButtonClick( _
        ByVal sender As Object, _
        ByVal e As EventArgs)

        SelectDefaultProperties()
    End Sub

    Private Sub SelectAllButtonClick( _
        ByVal sender As Object, _
        ByVal e As EventArgs)

        SelectedList.Items.Clear()

        For Each propertyInfo As PropertyColumnInfo In AllProperties
            SelectedList.Items.Add(propertyInfo)
        Next

        RefreshAvailableChecks()
    End Sub

    Private Sub ClearAllButtonClick( _
        ByVal sender As Object, _
        ByVal e As EventArgs)

        SelectedList.Items.Clear()
        RefreshAvailableChecks()
    End Sub

    Private Sub RefreshAvailableChecks()
        For index As Integer = 0 To AvailableList.Items.Count - 1
            Dim propertyInfo As PropertyColumnInfo = _
                CType(AvailableList.Items(index), PropertyColumnInfo)

            AvailableList.SetItemChecked( _
                index, _
                IsPropertyInSelectedList(propertyInfo.Key))
        Next
    End Sub

    Private Function IsPropertyInSelectedList( _
        ByVal propertyKey As String) As Boolean

        For Each selectedObject As Object In SelectedList.Items
            Dim propertyInfo As PropertyColumnInfo = _
                CType(selectedObject, PropertyColumnInfo)

            If String.Equals( _
                propertyInfo.Key, _
                propertyKey, _
                StringComparison.OrdinalIgnoreCase) Then
                Return True
            End If
        Next

        Return False
    End Function

    Private Sub ScanModeChanged(ByVal sender As Object, ByVal e As EventArgs)
        If ScanModeInfoLabel Is Nothing OrElse ScanModeBox Is Nothing Then Exit Sub
        Select Case ScanModeBox.SelectedIndex
            Case 0
                ScanModeInfoLabel.Text = "FAST: Core BOM tối thiểu, bỏ Drawing Index/Geometry/Deep Check."
            Case 2
                ScanModeInfoLabel.Text = "DEEP: Core + Drawing Index + preload Geometry toàn bộ Part."
            Case Else
                ScanModeInfoLabel.Text = "NORMAL: Core + Drawing cơ bản, Geometry vẫn Lazy."
        End Select
    End Sub

    Private Sub ExportButtonClick( _
        ByVal sender As Object, _
        ByVal e As EventArgs)

        SelectedProperties.Clear()

        For Each selectedObject As Object In SelectedList.Items
            SelectedProperties.Add( _
                CType(selectedObject, PropertyColumnInfo))
        Next

        IncludeFileName = FileNameCheckBox.Checked
        IncludeFilePath = FilePathCheckBox.Checked
        IncludeParentAssembly = ParentAssemblyCheckBox.Checked
        OpenExcelAfterExport = OpenExcelCheckBox.Checked
        Select Case ScanModeBox.SelectedIndex
            Case 0 : SelectedScanMode = BomScanMode.Fast
            Case 2 : SelectedScanMode = BomScanMode.Deep
            Case Else : SelectedScanMode = BomScanMode.Normal
        End Select

        If SelectedProperties.Count = 0 AndAlso _
           Not IncludeFileName AndAlso _
           Not IncludeFilePath AndAlso _
           Not IncludeParentAssembly Then

            MessageBox.Show( _
                "Hãy chọn ít nhất một cột để xuất.", _
                "BOM TOOL PRO", _
                MessageBoxButtons.OK, _
                MessageBoxIcon.Warning)
            Exit Sub
        End If

        Me.DialogResult = DialogResult.OK
        Me.Close()
    End Sub

    Private Sub CancelButtonClick( _
        ByVal sender As Object, _
        ByVal e As EventArgs)

        Me.DialogResult = DialogResult.Cancel
        Me.Close()
    End Sub
End Class

'====================================================================
' PROGRESS FORM
'====================================================================

'####################################################################
' SECTION 12 - PROGRESS / CANCEL UI
' Form tiến trình, trạng thái và hủy thao tác an toàn.
'####################################################################

Public Class BomProgressForm
    Inherits Form

    Private ProgressControl As ProgressBar
    Private StatusLabel As Label
    Private PercentLabel As Label
    Private CancelProcessButton As Button

    Public CancelRequested As Boolean = False

    Public Sub New()
        Me.Text = "BOM TOOL PRO - PROCESSING"
        Me.StartPosition = FormStartPosition.CenterScreen
        Me.Size = New Size(580, 235)
        Me.MinimumSize = New Size(580, 235)
        Me.MaximumSize = New Size(580, 235)
        Me.MaximizeBox = False
        Me.MinimizeBox = False
        Me.ControlBox = False
        Me.TopMost = False
        Me.ShowInTaskbar = False
        Me.Font = New Font("Segoe UI", 9.0F)
        Me.BackColor = Color.FromArgb(245, 247, 250)

        Dim titleLabel As New Label()
        titleLabel.Text = "ĐANG XỬ LÝ BOM"
        titleLabel.Font = New Font("Segoe UI", 13.0F, FontStyle.Bold)
        titleLabel.ForeColor = Color.FromArgb(31, 78, 121)
        titleLabel.AutoSize = True
        titleLabel.Location = New Point(20, 17)
        Me.Controls.Add(titleLabel)

        StatusLabel = New Label()
        StatusLabel.Text = "Đang chuẩn bị..."
        StatusLabel.Location = New Point(22, 52)
        StatusLabel.Size = New Size(530, 63)
        StatusLabel.AutoEllipsis = True
        Me.Controls.Add(StatusLabel)

        ProgressControl = New ProgressBar()
        ProgressControl.Location = New Point(22, 124)
        ProgressControl.Size = New Size(455, 25)
        ProgressControl.Minimum = 0
        ProgressControl.Maximum = 100
        ProgressControl.Value = 0
        ProgressControl.Style = ProgressBarStyle.Continuous
        Me.Controls.Add(ProgressControl)

        PercentLabel = New Label()
        PercentLabel.Text = "0%"
        PercentLabel.Font = New Font("Segoe UI", 9.0F, FontStyle.Bold)
        PercentLabel.TextAlign = ContentAlignment.MiddleCenter
        PercentLabel.Location = New Point(482, 124)
        PercentLabel.Size = New Size(50, 25)
        Me.Controls.Add(PercentLabel)

        CancelProcessButton = New Button()
        CancelProcessButton.Text = "HỦY"
        CancelProcessButton.Location = New Point(457, 163)
        CancelProcessButton.Size = New Size(75, 30)
        AddHandler CancelProcessButton.Click, AddressOf CancelProcessButtonClick
        Me.Controls.Add(CancelProcessButton)
    End Sub

    Public Sub SetProgress( _
        ByVal percent As Integer, _
        ByVal statusText As String)

        If percent < 0 Then percent = 0
        If percent > 100 Then percent = 100

        Try
            ProgressControl.Value = percent
        Catch
            ProgressControl.Value = 0
        End Try

        PercentLabel.Text = percent.ToString() & "%"
        StatusLabel.Text = statusText
        Me.Refresh()
        WinFormsApplication.DoEvents()
    End Sub

    Public Sub SetStatus(ByVal statusText As String)
        StatusLabel.Text = statusText
        Me.Refresh()
        WinFormsApplication.DoEvents()
    End Sub

    Private Sub CancelProcessButtonClick( _
        ByVal sender As Object, _
        ByVal e As EventArgs)

        CancelRequested = True
        CancelProcessButton.Enabled = False
        StatusLabel.Text = "Đang dừng an toàn..."
        Me.Refresh()
        WinFormsApplication.DoEvents()
    End Sub
End Class



'====================================================================
' UNIT ENGINE - GIỮ GIÁ TRỊ GỐC TRONG CACHE, CHỈ QUY ĐỔI KHI HIỂN THỊ
'====================================================================

'####################################################################
' SECTION 13 - UNIT ENGINE
' Quản lý đơn vị hiển thị và chuyển đổi dữ liệu.
'####################################################################

Public Class BomUnitManager
    Public Shared MassUnit As String = "kg"
    Public Shared LengthUnit As String = "mm"
    Public Shared AreaUnit As String = "cm²"
    Public Shared VolumeUnit As String = "cm³"

    Public Shared Function ConvertMass(ByVal valueKg As Double) As Double
        Select Case MassUnit.ToLowerInvariant()
            Case "g" : Return valueKg * 1000.0
            Case "mg" : Return valueKg * 1000000.0
            Case "lb" : Return valueKg * 2.20462262185
            Case "oz" : Return valueKg * 35.2739619496
            Case "ton" : Return valueKg / 1000.0
            Case Else : Return valueKg
        End Select
    End Function

    Public Shared Function ConvertLengthFromMm(ByVal valueMm As Double) As Double
        Select Case LengthUnit.ToLowerInvariant()
            Case "cm" : Return valueMm / 10.0
            Case "m" : Return valueMm / 1000.0
            Case "inch", "in" : Return valueMm / 25.4
            Case "ft" : Return valueMm / 304.8
            Case Else : Return valueMm
        End Select
    End Function

    'Inventor MassProperties.Area sử dụng cm² vì đơn vị cơ sở chiều dài là cm.
    Public Shared Function ConvertAreaFromCm2(ByVal valueCm2 As Double) As Double
        Select Case AreaUnit.ToLowerInvariant()
            Case "mm²", "mm2" : Return valueCm2 * 100.0
            Case "m²", "m2" : Return valueCm2 / 10000.0
            Case "inch²", "in²", "in2" : Return valueCm2 / 6.4516
            Case "ft²", "ft2" : Return valueCm2 / 929.0304
            Case Else : Return valueCm2
        End Select
    End Function

    'Inventor MassProperties.Volume sử dụng cm³.
    Public Shared Function ConvertVolumeFromCm3(ByVal valueCm3 As Double) As Double
        Select Case VolumeUnit.ToLowerInvariant()
            Case "mm³", "mm3" : Return valueCm3 * 1000.0
            Case "l", "liter", "litre" : Return valueCm3 / 1000.0
            Case "m³", "m3" : Return valueCm3 / 1000000.0
            Case "inch³", "in³", "in3" : Return valueCm3 / 16.387064
            Case "ft³", "ft3" : Return valueCm3 / 28316.846592
            Case Else : Return valueCm3
        End Select
    End Function

    Public Shared Function FormatValue(ByVal value As Double) As String
        If Math.Abs(value) >= 1000000 Then Return value.ToString("0.###E+0")
        If Math.Abs(value) >= 1000 Then Return value.ToString("0.###")
        If Math.Abs(value) >= 1 Then Return value.ToString("0.###")
        Return value.ToString("0.######")
    End Function

    Public Shared Function FormatMass(ByVal valueKg As Double) As String
        Return FormatValue(ConvertMass(valueKg))
    End Function

    Public Shared Function FormatLength(ByVal valueMm As Double) As String
        Return FormatValue(ConvertLengthFromMm(valueMm))
    End Function

    Public Shared Function FormatBoundingBox(ByVal item As PartBomItem) As String
        If item Is Nothing OrElse item.BoundingMaxMm <= 0 Then Return ""
        Return FormatLength(item.BoundingMaxMm) & " x " & FormatLength(item.BoundingMidMm) & " x " & FormatLength(item.BoundingMinMm)
    End Function

    Public Shared Function IsMassProperty(ByVal name As String) As Boolean
        Dim n As String = If(name, "").Trim().ToUpperInvariant()
        Return n = "MASS" OrElse n = "WEIGHT" OrElse n.Contains("MASS")
    End Function

    Public Shared Function IsVolumeProperty(ByVal name As String) As Boolean
        Dim n As String = If(name, "").Trim().ToUpperInvariant()
        Return n = "VOLUME" OrElse n.Contains("VOLUME")
    End Function

    Public Shared Function IsAreaProperty(ByVal name As String) As Boolean
        Dim n As String = If(name, "").Trim().ToUpperInvariant()
        Return n = "AREA" OrElse n = "SURFACE AREA" OrElse n.Contains("SURFACE AREA")
    End Function

    Public Shared Function GetPropertyHeader(ByVal propertyName As String) As String
        If IsMassProperty(propertyName) Then Return propertyName.ToUpperInvariant() & " (" & MassUnit & ")"
        If IsVolumeProperty(propertyName) Then Return propertyName.ToUpperInvariant() & " (" & VolumeUnit & ")"
        If IsAreaProperty(propertyName) Then Return propertyName.ToUpperInvariant() & " (" & AreaUnit & ")"
        Return propertyName.ToUpperInvariant()
    End Function

    Public Shared Function GetPropertyDisplayValue(ByVal item As PartBomItem, ByVal propertyInfo As PropertyColumnInfo) As Object
        If item Is Nothing OrElse propertyInfo Is Nothing Then Return ""
        If IsMassProperty(propertyInfo.PropertyName) Then Return ConvertMass(item.Mass)
        If IsVolumeProperty(propertyInfo.PropertyName) Then Return ConvertVolumeFromCm3(item.Volume)
        If IsAreaProperty(propertyInfo.PropertyName) Then Return ConvertAreaFromCm2(item.SurfaceArea)
        If item.SelectedPropertyValues.ContainsKey(propertyInfo.Key) Then Return item.SelectedPropertyValues(propertyInfo.Key)
        Return ""
    End Function
End Class

'====================================================================
' LỊCH SỬ CHỈNH SỬA IPROPERTY - UNDO / REDO
'====================================================================

'####################################################################
' SECTION 14 - EDIT HISTORY / VIEWER REGISTRY
' Undo/Redo action model và registry của Viewer.
'####################################################################

Public Class BomEditAction
    Public DocumentKey As String = ""
    Public PropertyKey As String = ""
    Public OldValue As String = ""
    Public NewValue As String = ""
    Public PropertyInfo As PropertyColumnInfo = Nothing
End Class

'====================================================================
' PHASE 2 - TRANSACTION ENGINE / STAGING MODEL
'====================================================================
Public Class BomPropertyChange
    Public DocumentKey As String = ""
    Public DocumentPath As String = ""
    Public PartNumber As String = ""
    Public FileName As String = ""
    Public PropertyKey As String = ""
    Public PropertyInfo As PropertyColumnInfo = Nothing
    Public OldValue As String = ""
    Public NewValue As String = ""
    'Quan trọng cho Custom iProperty: False nghĩa là trước Commit property chưa tồn tại.
    'Undo/Rollback phải DELETE property vừa tạo thay vì để lại một property rỗng.
    Public PropertyExistedBefore As Boolean = True
    Public Status As String = "PENDING"
    Public ErrorMessage As String = ""
End Class


Public Class BomPendingTransactionStore
    Private Shared Function Enc(ByVal value As String) As String
        Return Convert.ToBase64String(System.Text.Encoding.UTF8.GetBytes(If(value, "")))
    End Function

    Private Shared Function Dec(ByVal value As String) As String
        Try
            Return System.Text.Encoding.UTF8.GetString(Convert.FromBase64String(If(value, "")))
        Catch
            Return ""
        End Try
    End Function

    Public Shared Sub Save(ByVal filePath As String, ByVal assemblyPath As String, ByVal tx As BomTransaction)
        If String.IsNullOrWhiteSpace(filePath) Then Exit Sub
        If tx Is Nothing OrElse tx.Changes Is Nothing OrElse tx.Changes.Count = 0 Then
            Try
                If System.IO.File.Exists(filePath) Then System.IO.File.Delete(filePath)
            Catch
            End Try
            Exit Sub
        End If

        Dim lines As New List(Of String)()
        lines.Add("FORMAT=3")
        lines.Add("ASSEMBLY=" & Enc(assemblyPath))
        lines.Add("NAME=" & Enc(tx.Name))
        lines.Add("CREATED=" & tx.CreatedAt.ToString("o"))
        For Each ch As BomPropertyChange In tx.Changes
            Dim propName As String = ""
            Try
                If ch.PropertyInfo IsNot Nothing Then propName = ch.PropertyInfo.PropertyName
            Catch
            End Try
            lines.Add("CHANGE|" &
                      Enc(ch.DocumentPath) & "|" &
                      Enc(ch.DocumentKey) & "|" &
                      Enc(ch.PartNumber) & "|" &
                      Enc(ch.PropertyKey) & "|" &
                      Enc(propName) & "|" &
                      Enc(ch.OldValue) & "|" &
                      Enc(ch.NewValue) & "|" &
                      Enc(ch.Status) & "|" &
                      Enc(If(ch.PropertyExistedBefore, "1", "0")))
        Next
        System.IO.File.WriteAllLines(filePath, lines.ToArray(), System.Text.Encoding.UTF8)
    End Sub

    Public Shared Function Load(ByVal filePath As String,
                                ByRef assemblyPath As String,
                                ByRef transactionName As String,
                                ByRef createdAt As DateTime) As List(Of BomPropertyChange)
        Dim result As New List(Of BomPropertyChange)()
        assemblyPath = ""
        transactionName = "RECOVERED BOM EDIT"
        createdAt = DateTime.MinValue
        If String.IsNullOrWhiteSpace(filePath) OrElse Not System.IO.File.Exists(filePath) Then Return result

        Try
            For Each line As String In System.IO.File.ReadAllLines(filePath, System.Text.Encoding.UTF8)
                If line.StartsWith("ASSEMBLY=", StringComparison.OrdinalIgnoreCase) Then
                    assemblyPath = Dec(line.Substring(9))
                ElseIf line.StartsWith("NAME=", StringComparison.OrdinalIgnoreCase) Then
                    transactionName = Dec(line.Substring(5))
                ElseIf line.StartsWith("CREATED=", StringComparison.OrdinalIgnoreCase) Then
                    DateTime.TryParse(line.Substring(8), createdAt)
                ElseIf line.StartsWith("CHANGE|", StringComparison.OrdinalIgnoreCase) Then
                    Dim p() As String = line.Split("|"c)
                    If p.Length >= 9 Then
                        Dim ch As New BomPropertyChange()
                        ch.DocumentPath = Dec(p(1))
                        ch.DocumentKey = Dec(p(2))
                        ch.PartNumber = Dec(p(3))
                        ch.PropertyKey = Dec(p(4))
                        Dim propertyName As String = Dec(p(5))
                        ch.OldValue = Dec(p(6))
                        ch.NewValue = Dec(p(7))
                        ch.Status = Dec(p(8))
                        'FORMAT 3 lưu thêm trạng thái property có tồn tại trước edit hay không.
                        'File recovery cũ (FORMAT 2) mặc định True để rollback an toàn, không xóa nhầm property cũ.
                        ch.PropertyExistedBefore = True
                        If p.Length >= 10 Then ch.PropertyExistedBefore = String.Equals(Dec(p(9)), "1", StringComparison.OrdinalIgnoreCase)
                        ch.ErrorMessage = propertyName 'temporary carrier until PropertyInfo is resolved
                        result.Add(ch)
                    End If
                End If
            Next
        Catch ex As Exception
            BomLogger.Error("RECOVERY", "Pending transaction read failed: " & ex.Message)
        End Try
        Return result
    End Function

    Public Shared Sub Delete(ByVal filePath As String)
        Try
            If Not String.IsNullOrWhiteSpace(filePath) AndAlso System.IO.File.Exists(filePath) Then System.IO.File.Delete(filePath)
        Catch ex As Exception
            BomLogger.Warn("RECOVERY", "Cannot delete recovery file: " & ex.Message)
        End Try
    End Sub
End Class

Public Class BomTransaction
    Public Name As String = "BOM EDIT"
    Public CreatedAt As DateTime = DateTime.Now
    Public Changes As New List(Of BomPropertyChange)()
    Public Status As String = "PENDING"
    Public Atomic As Boolean = True
    Public AppliedCount As Integer = 0
    Public FailedCount As Integer = 0
    Public NotProcessedCount As Integer = 0
    Public RollbackFailedCount As Integer = 0
End Class

'====================================================================
' GIỮ MỘT BOM VIEWER DUY NHẤT
'====================================================================
Public Enum BomAssemblySwitchResult
    NoViewer = 0
    SameAssembly = 1
    DifferentAssembly = 2
    SwitchConfirmed = 3
    SwitchCancelled = 4
    SwitchFailed = 5
End Enum

Public Class BomViewerRegistry
    Public Shared CurrentViewer As BomViewerForm = Nothing
    Public Shared CurrentAssemblyPath As String = ""

    Public Shared Function NormalizePath(ByVal pathValue As String) As String
        If String.IsNullOrWhiteSpace(pathValue) Then Return ""
        Try
            Return System.IO.Path.GetFullPath(pathValue).Trim()
        Catch
            Return pathValue.Trim()
        End Try
    End Function

    Public Shared Function HasActiveViewer() As Boolean
        Try
            Return CurrentViewer IsNot Nothing AndAlso
                   Not CurrentViewer.IsDisposed AndAlso
                   Not CurrentViewer.Disposing
        Catch
            CurrentViewer = Nothing
            CurrentAssemblyPath = ""
            Return False
        End Try
    End Function

    Public Shared Function IsSameAssembly(ByVal assemblyPath As String) As Boolean
        If Not HasActiveViewer() Then Return False
        Return String.Equals(NormalizePath(CurrentAssemblyPath),
                             NormalizePath(assemblyPath),
                             StringComparison.OrdinalIgnoreCase)
    End Function

    Public Shared Function TryActivateExistingViewer() As Boolean
        If Not HasActiveViewer() Then Return False
        Try
            If CurrentViewer.WindowState = FormWindowState.Minimized Then
                CurrentViewer.WindowState = FormWindowState.Normal
            End If
            CurrentViewer.Show()
            CurrentViewer.BringToFront()
            CurrentViewer.Activate()
            CurrentViewer.Focus()
            Return True
        Catch
            Return False
        End Try
    End Function

    Public Shared Sub Register(ByVal viewer As BomViewerForm, ByVal assemblyPath As String)
        CurrentViewer = viewer
        CurrentAssemblyPath = NormalizePath(assemblyPath)
        BomSingleInstanceManager.Register(viewer)
    End Sub

    Public Shared Sub UpdateAssembly(ByVal assemblyPath As String)
        CurrentAssemblyPath = NormalizePath(assemblyPath)
    End Sub

    Public Shared Sub Unregister(ByVal viewer As BomViewerForm)
        If CurrentViewer Is viewer Then
            CurrentViewer = Nothing
            CurrentAssemblyPath = ""
        End If
        BomSingleInstanceManager.Unregister(viewer)
    End Sub
End Class

'====================================================================
' BOM VIEWER MODELESS - KHÔNG KHÓA INVENTOR
'====================================================================

'####################################################################
' SECTION 15 - MAIN BOM VIEWER FORM
' Giao diện chính, Ribbon, Grid, Search, Assembly, Drawing, Excel và Inventor interaction.
'####################################################################

Public Class BomViewerForm
    Inherits Form

    Public ReadOnly Property CurrentAssemblyPath As String
        Get
            Return _assemblyPath
        End Get
    End Property

    Public ReadOnly Property PendingChangeCount As Integer
        Get
            If _pendingTransaction Is Nothing OrElse _pendingTransaction.Changes Is Nothing Then Return 0
            Return _pendingTransaction.Changes.Count
        End Get
    End Property

    Private _inventor As Inventor.Application
    Private _assemblyPath As String
    Private _assemblyName As String
    Private _allItems As List(Of PartBomItem)
    Private _selectedProperties As List(Of PropertyColumnInfo)
    Private _includeFileName As Boolean
    Private _includeFilePath As Boolean
    Private _includeParentAssembly As Boolean
    Private _exportCallback As System.Action(Of List(Of PartBomItem))
    Private _refreshCallback As System.Action(Of List(Of PartBomItem))
    Private _loadBomCallback As System.Action
    Private _loadedAt As DateTime
    Private _layoutFile As String
    Private _suppressCellWrite As Boolean = False
    Private _selectionTimer As System.Windows.Forms.Timer
    Private _inventorSyncTimer As System.Windows.Forms.Timer
    Private _searchTimer As System.Windows.Forms.Timer
    Private _bomHighlightSet As Inventor.HighlightSet
    Private _syncingSelection As Boolean = False
    Private _autoHighlightOnClick As Boolean = False
    Private _autoZoomOnClick As Boolean = False
    Private _highlightAllOccurrences As Boolean = True
    Private _syncInventorToBom As Boolean = True
    Private _lastInventorSelectionKey As String = ""
    Private _menuAutoHighlight As ToolStripMenuItem
    Private _menuAutoZoom As ToolStripMenuItem
    Private _menuHighlightAll As ToolStripMenuItem
    Private _menuTwoWaySync As ToolStripMenuItem
    Private _drawingIndex As New Dictionary(Of String, String)(StringComparer.OrdinalIgnoreCase)
    Private _manualDrawingMap As New Dictionary(Of String, String)(StringComparer.OrdinalIgnoreCase)
    Private _drawingMapFile As String
    Private _groupedView As Boolean = True
    Private _bomDisplayMode As BomDisplayMode = BomDisplayMode.Hybrid
    Private _structureRoot As BomAssemblyNode = Nothing
    Private _activeSnapshot As BomSnapshot = Nothing
    Private _lastChangeSet As BomChangeSet = Nothing
    Private _quickFilterMode As String = "ALL"
    Private _collapsedGroups As New HashSet(Of String)(StringComparer.OrdinalIgnoreCase)
    Private _markedPartKeys As New HashSet(Of String)(StringComparer.OrdinalIgnoreCase)
    Private _displayModeButton As System.Windows.Forms.ToolStripButton
    Private _undoStack As New Stack(Of BomEditAction)()
    Private _redoStack As New Stack(Of BomEditAction)()
    Private _editOriginalValue As String = ""
    Private _pendingTransaction As New BomTransaction()
    Private _transactionUndo As New Stack(Of BomTransaction)()
    Private _transactionRedo As New Stack(Of BomTransaction)()
    Private _committedDocumentKeys As New HashSet(Of String)(StringComparer.OrdinalIgnoreCase)
    Private _transactionAtomic As Boolean = True
    Private _editDocumentKey As String = ""
    Private _editPropertyKey As String = ""
    'EXCEL-LIKE FILL HANDLE
    Private _fillDragging As Boolean = False
    Private _fillSourceRow As Integer = -1
    Private _fillSourceColumn As Integer = -1
    Private _fillTargetRow As Integer = -1
    Private Const FillHandleSize As Integer = 7
    Private _isolateOccurrences As New List(Of ComponentOccurrence)()
    Private _isolateVisibility As New List(Of Boolean)()
    Private _runtimeIndex As New BomRuntimeIndex()
    Private _isBusy As Boolean = False
    Private _busyOperation As String = ""
    Private _lastRefreshDurationMs As Long = 0
    'V20 - PERFORMANCE / SMART CACHE STATE
    Private _performance As New BomPerformanceSnapshot()
    Private _rootAssemblySignature As String = ""
    Private _scanMode As BomScanMode = BomScanMode.Normal
    'PRO MAX - SAFETY / SESSION
    Private _safeMode As Boolean = False
    Private _sessionFile As String = ""
    Private _pendingRecoveryFile As String = ""
    Private _config As New BomConfig()
    Private StatusSafeMode As System.Windows.Forms.ToolStripStatusLabel
    Private StatusPending As System.Windows.Forms.ToolStripStatusLabel

    Private SearchBox As TextBox
    Private AssemblyFilterBox As ComboBox
    Private AssemblyFilterInfo As Label
    Private Grid As DataGridView
    Private SourceLabel As Label
    Private ContextMenu As ContextMenuStrip
    Private ToolBar As System.Windows.Forms.ToolStrip
    Private RibbonHost As Panel
    Private MainLayout As System.Windows.Forms.TableLayoutPanel
    Private RibbonTabBar As System.Windows.Forms.FlowLayoutPanel
    Private RibbonContent As Panel
    Private RibbonQuickBar As System.Windows.Forms.FlowLayoutPanel
    Private RibbonCollapseButton As Button
    Private _activeRibbonTab As String = "HOME"
    Private _ribbonCollapsed As Boolean = False
    Private _ribbonTabButtons As New Dictionary(Of String, Button)(StringComparer.OrdinalIgnoreCase)
    Private StatusBar As System.Windows.Forms.StatusStrip
    Private StatusAssembly As System.Windows.Forms.ToolStripStatusLabel
    Private StatusParts As System.Windows.Forms.ToolStripStatusLabel
    Private StatusVisible As System.Windows.Forms.ToolStripStatusLabel
    Private StatusQty As System.Windows.Forms.ToolStripStatusLabel
    Private StatusDrawing As System.Windows.Forms.ToolStripStatusLabel
    Private StatusLoadTime As System.Windows.Forms.ToolStripStatusLabel
    Private StatusSelection As System.Windows.Forms.ToolStripStatusLabel
    Private ExcelNameBox As TextBox
    Private ExcelFormulaBox As TextBox
    Private ExcelFormulaApply As Button
    Private _lastSelectedColumn As Integer = -1
    Private _lastSelectedRow As Integer = -1
    'HYBRID SELECTION: Excel cell mode + true FullRowSelect when requested.
    Private _forceFullRowSelection As Boolean = False
    Private _cutMode As Boolean = False
    Private _excelHeaderTitles As New Dictionary(Of String, String)(StringComparer.OrdinalIgnoreCase)
    Private _contextColumnIndex As Integer = -1
    Private _contextRowIndex As Integer = -1

    'V13.2 - GROUP SAFE SORT
    'Không dùng DataGridView Automatic Sort vì Assembly Header là dòng điều khiển,
    'không phải dữ liệu BOM. Sort được thực hiện trên PartBomItem trước khi render.
    Private _activeSortColumn As String = ""
    Private _activeSortDirection As System.ComponentModel.ListSortDirection = System.ComponentModel.ListSortDirection.Ascending

    'ON-DEMAND FEATURE ENGINE
    Private _enabledFeatures As New HashSet(Of String)(StringComparer.OrdinalIgnoreCase)
    Private _featureRegistry As New Dictionary(Of String, BomFeatureDefinition)(StringComparer.OrdinalIgnoreCase)
    Private _thumbnailCache As New Dictionary(Of String, System.Drawing.Image)(StringComparer.OrdinalIgnoreCase)
    Private _featureManagerButton As System.Windows.Forms.ToolStripButton
    Private MainSplit As System.Windows.Forms.SplitContainer
    Private PreviewPanel As Panel
    Private PreviewImage As PictureBox
    Private PreviewTitle As Label
    Private PreviewInfo As Label
    Private DetailTabs As TabControl
    Private DetailPropertyText As TextBox
    Private DetailContextText As TextBox
    Private DetailActions As FlowLayoutPanel
    Private _detailPanelWidth As Integer = 340
    Private _detailPanelVisible As Boolean = True
    Private _selectedColumnProfile As String = "ENGINEERING"
    Private _quickButtons As New Dictionary(Of String, Button)(StringComparer.OrdinalIgnoreCase)


'####################################################################
' SUBSECTION 15.01 - CONSTRUCTOR / FORM INITIALIZATION
'####################################################################

    Public Sub New( _
        ByVal inventorApplication As Inventor.Application, _
        ByVal assemblyPath As String, _
        ByVal assemblyName As String, _
        ByVal items As List(Of PartBomItem), _
        ByVal selectedProperties As List(Of PropertyColumnInfo), _
        ByVal includeFileName As Boolean, _
        ByVal includeFilePath As Boolean, _
        ByVal includeParentAssembly As Boolean, _
        ByVal exportCallback As System.Action(Of List(Of PartBomItem)), _
        ByVal refreshCallback As System.Action(Of List(Of PartBomItem)), _
        ByVal loadBomCallback As System.Action, _
        ByVal scanMode As BomScanMode)

        _inventor = inventorApplication
        _assemblyPath = assemblyPath
        _assemblyName = assemblyName
        _allItems = items
        _selectedProperties = selectedProperties
        _includeFileName = includeFileName
        _includeFilePath = includeFilePath
        _includeParentAssembly = includeParentAssembly
        _exportCallback = exportCallback
        _refreshCallback = refreshCallback
        _loadBomCallback = loadBomCallback
        _scanMode = scanMode
        _performance.LastMode = _scanMode.ToString().ToUpperInvariant()
        _loadedAt = DateTime.Now
        _rootAssemblySignature = BomSignatureEngine.FileSignature(_assemblyPath)
        For Each signatureItem As PartBomItem In _allItems
            If signatureItem IsNot Nothing AndAlso signatureItem.SignatureCapturedAt = DateTime.MinValue Then BomSignatureEngine.CaptureIntoItem(signatureItem)
        Next
        _runtimeIndex.Build(_assemblyName, _allItems)
        RegisterBuiltInFeatures()
        RegisterUiCommands()

        Dim configFolder As String = IOPath.Combine( _
            System.Environment.GetFolderPath(System.Environment.SpecialFolder.MyDocuments), _
            "BOMToolByHieu")
        Try
            If Not System.IO.Directory.Exists(configFolder) Then System.IO.Directory.CreateDirectory(configFolder)
        Catch
        End Try
        _layoutFile = IOPath.Combine(configFolder, "BOM_VIEWER_LAYOUT.txt")
        _drawingMapFile = IOPath.Combine(configFolder, "DRAWING_PATH_MAP.txt")
        _sessionFile = IOPath.Combine(configFolder, "BOM_SESSION_STATE.txt")
        _pendingRecoveryFile = IOPath.Combine(configFolder, "BOM_PENDING_TRANSACTION.txt")
        _safeMode = _config.SafeModeDefault
        _transactionAtomic = _config.AtomicTransactionDefault

        BuildInterface()
        BuildColumns()
        LoadManualDrawingMap()

        If _scanMode <> BomScanMode.Fast Then
            SourceLabel.Text = "Đang xác định vị trí Drawing..."
            WinFormsApplication.DoEvents()
            BuildDrawingIndex()
        Else
            _drawingIndex.Clear()
        End If

        If _scanMode = BomScanMode.Deep Then
            SourceLabel.Text = "DEEP MODE - đang nạp Geometry..."
            WinFormsApplication.DoEvents()
            Dim deepIndex As Integer = 0
            For Each deepItem As PartBomItem In _allItems
                BomGeometryEngine.EnsureLoaded(deepItem)
                deepIndex += 1
                If deepIndex Mod 25 = 0 Then WinFormsApplication.DoEvents()
            Next
        End If

        SourceLabel.Text = "Nguồn: " & _assemblyPath & "  |  MODE: " & _scanMode.ToString().ToUpperInvariant()
        BuildAssemblyFilterItems()
        LoadRows()
        TryLoadLayout(False)
        RestoreSessionState()
        RestorePendingTransactionIfAvailable()
        UpdateSafeModeUI()
    End Sub

    Public Sub ReplaceAssemblyData( _
        ByVal assemblyPath As String, _
        ByVal assemblyName As String, _
        ByVal items As List(Of PartBomItem), _
        ByVal selectedProperties As List(Of PropertyColumnInfo), _
        ByVal includeFileName As Boolean, _
        ByVal includeFilePath As Boolean, _
        ByVal includeParentAssembly As Boolean, _
        ByVal exportCallback As System.Action(Of List(Of PartBomItem)), _
        ByVal refreshCallback As System.Action(Of List(Of PartBomItem)), _
        ByVal loadBomCallback As System.Action, _
        ByVal scanMode As BomScanMode)

        'Atomic UI/data swap: caller only invokes this after successful scan.
        If items Is Nothing Then Throw New ArgumentNullException("items")
        If selectedProperties Is Nothing Then selectedProperties = New List(Of PropertyColumnInfo)()

        Me.SuspendLayout()
        Try
            _assemblyPath = assemblyPath
            _assemblyName = assemblyName
            _allItems = items
            _selectedProperties = selectedProperties
            _includeFileName = includeFileName
            _includeFilePath = includeFilePath
            _includeParentAssembly = includeParentAssembly
            _exportCallback = exportCallback
            _refreshCallback = refreshCallback
            _loadBomCallback = loadBomCallback
            _scanMode = scanMode
            _loadedAt = DateTime.Now
            _rootAssemblySignature = BomSignatureEngine.FileSignature(_assemblyPath)

            _pendingTransaction = New BomTransaction()
            _undoStack.Clear()
            _redoStack.Clear()
            _drawingIndex.Clear()
            _runtimeIndex.Build(_assemblyName, _allItems)

            If _scanMode <> BomScanMode.Fast Then BuildDrawingIndex()

            BuildAssemblyFilterItems()
            BuildColumns()
            LoadRows()

            Me.Text = BomConstants.ToolVersion & " - " & _assemblyName
            If SourceLabel IsNot Nothing Then
                SourceLabel.Text = "Nguồn: " & _assemblyPath & "  |  MODE: " & _scanMode.ToString().ToUpperInvariant()
            End If

            UpdatePendingCaption()
            UpdateSafeModeUI()
            SaveSessionState()
            BomViewerRegistry.UpdateAssembly(_assemblyPath)

            If StatusSelection IsNot Nothing Then
                StatusSelection.Text = "Loaded: " & _assemblyName
            End If
        Finally
            Me.ResumeLayout(True)
        End Try
    End Sub


'####################################################################
' SUBSECTION 15.02 - INTERFACE LAYOUT / CONTROL CREATION
'####################################################################

    Private Sub BuildInterface()
        Me.Text = BomConstants.ToolVersion & " - " & _assemblyName
        Me.StartPosition = FormStartPosition.CenterScreen
        Me.WindowState = System.Windows.Forms.FormWindowState.Maximized
        Me.Size = New Size(1440, 860)
        Me.MinimumSize = New Size(1050, 650)
        Me.Font = New Font("Segoe UI", 9.0F)
        Me.BackColor = Color.White
        Me.TopMost = False
        Me.ShowInTaskbar = True

        Dim root As New System.Windows.Forms.TableLayoutPanel()
        MainLayout = root
        root.Dock = DockStyle.Fill
        root.ColumnCount = 1
        root.RowCount = 5
        root.RowStyles.Add(New System.Windows.Forms.RowStyle(System.Windows.Forms.SizeType.Absolute, 136.0F))
        root.RowStyles.Add(New System.Windows.Forms.RowStyle(System.Windows.Forms.SizeType.Absolute, 76.0F))
        root.RowStyles.Add(New System.Windows.Forms.RowStyle(System.Windows.Forms.SizeType.Absolute, 34.0F))
        root.RowStyles.Add(New System.Windows.Forms.RowStyle(System.Windows.Forms.SizeType.Percent, 100.0F))
        root.RowStyles.Add(New System.Windows.Forms.RowStyle(System.Windows.Forms.SizeType.Absolute, 28.0F))
        root.Padding = New System.Windows.Forms.Padding(8)
        Me.Controls.Add(root)

        BuildRibbonHost()
        root.Controls.Add(RibbonHost, 0, 0)

        Dim infoPanel As New Panel()
        infoPanel.Dock = DockStyle.Fill
        infoPanel.BackColor = Color.White
        infoPanel.Padding = New System.Windows.Forms.Padding(14, 8, 14, 8)
        root.Controls.Add(infoPanel, 0, 1)

        Dim title As New Label()
        title.Text = "INVENTOR ASSEMBLY DATA CONTROL CENTER"
        title.Font = New Font("Segoe UI Semibold", 14.0F, FontStyle.Bold)
        title.ForeColor = Color.FromArgb(45, 92, 112)
        title.AutoSize = True
        title.Location = New Point(14, 8)
        infoPanel.Controls.Add(title)

        SourceLabel = New Label()
        SourceLabel.Text = "Nguồn: " & _assemblyPath
        SourceLabel.AutoEllipsis = True
        SourceLabel.ForeColor = Color.FromArgb(90, 110, 120)
        SourceLabel.Location = New Point(16, 42)
        SourceLabel.Size = New Size(820, 20)
        SourceLabel.Anchor = AnchorStyles.Top Or AnchorStyles.Left Or AnchorStyles.Right
        infoPanel.Controls.Add(SourceLabel)

        Dim searchPanel As New Panel()
        searchPanel.Size = New Size(700, 58)
        searchPanel.Anchor = AnchorStyles.Top Or AnchorStyles.Right
        searchPanel.Location = New Point(infoPanel.ClientSize.Width - 714, 7)
        AddHandler infoPanel.Resize, Sub(sender As Object, e As EventArgs)
            searchPanel.Left = Math.Max(500, infoPanel.ClientSize.Width - searchPanel.Width - 14)
            SourceLabel.Width = Math.Max(250, searchPanel.Left - 30)
        End Sub
        infoPanel.Controls.Add(searchPanel)

        Dim assemblyCaption As New Label()
        assemblyCaption.Text = "Assembly"
        assemblyCaption.AutoSize = True
        assemblyCaption.ForeColor = Color.FromArgb(70, 95, 105)
        assemblyCaption.Location = New Point(0, 8)
        searchPanel.Controls.Add(assemblyCaption)

        AssemblyFilterBox = New ComboBox()
        AssemblyFilterBox.DropDownStyle = ComboBoxStyle.DropDown
        AssemblyFilterBox.AutoCompleteMode = System.Windows.Forms.AutoCompleteMode.SuggestAppend
        AssemblyFilterBox.AutoCompleteSource = System.Windows.Forms.AutoCompleteSource.ListItems
        AssemblyFilterBox.Location = New Point(72, 4)
        AssemblyFilterBox.Size = New Size(260, 26)
        AddHandler AssemblyFilterBox.SelectedIndexChanged, AddressOf AssemblyFilterChanged
        AddHandler AssemblyFilterBox.TextChanged, AddressOf AssemblyFilterChanged
        searchPanel.Controls.Add(AssemblyFilterBox)

        AssemblyFilterInfo = New Label()
        AssemblyFilterInfo.Text = "Tất cả Assembly"
        AssemblyFilterInfo.AutoEllipsis = True
        AssemblyFilterInfo.ForeColor = Color.FromArgb(35, 120, 135)
        AssemblyFilterInfo.Location = New Point(340, 8)
        AssemblyFilterInfo.Size = New Size(355, 20)
        searchPanel.Controls.Add(AssemblyFilterInfo)

        Dim searchCaption As New Label()
        searchCaption.Text = "Tìm kiếm"
        searchCaption.AutoSize = True
        searchCaption.ForeColor = Color.FromArgb(70, 95, 105)
        searchCaption.Location = New Point(0, 37)
        searchPanel.Controls.Add(searchCaption)

        SearchBox = New TextBox()
        SearchBox.Location = New Point(72, 33)
        SearchBox.Size = New Size(623, 26)
        SearchBox.BorderStyle = System.Windows.Forms.BorderStyle.FixedSingle
        AddHandler SearchBox.TextChanged, AddressOf SearchChanged
        searchPanel.Controls.Add(SearchBox)

        BuildExcelFormulaBar(root)

        Grid = New DataGridView()
        EnableGridDoubleBuffer(Grid)
        Grid.Dock = DockStyle.Fill
        Grid.BackgroundColor = Color.White
        Grid.BorderStyle = System.Windows.Forms.BorderStyle.FixedSingle
        Grid.AllowUserToAddRows = False
        Grid.AllowUserToDeleteRows = False
        Grid.AllowUserToOrderColumns = True
        Grid.AllowUserToResizeColumns = True
        Grid.AllowUserToResizeRows = True
        Grid.ReadOnly = False
        Grid.MultiSelect = True
        Grid.SelectionMode = DataGridViewSelectionMode.CellSelect
        Grid.ClipboardCopyMode = System.Windows.Forms.DataGridViewClipboardCopyMode.EnableWithoutHeaderText
        Grid.AutoSizeColumnsMode = DataGridViewAutoSizeColumnsMode.None
        Grid.AutoSizeRowsMode = System.Windows.Forms.DataGridViewAutoSizeRowsMode.None
        Grid.RowTemplate.Height = 27
        Grid.RowHeadersVisible = True
        Grid.RowHeadersWidth = 46
        Grid.RowHeadersDefaultCellStyle.BackColor = Color.FromArgb(242, 246, 248)
        Grid.RowHeadersDefaultCellStyle.ForeColor = Color.FromArgb(55, 75, 85)
        Grid.RowHeadersDefaultCellStyle.SelectionBackColor = Color.FromArgb(191, 225, 235)
        Grid.EnableHeadersVisualStyles = False
        Grid.ColumnHeadersDefaultCellStyle.BackColor = Color.FromArgb(242, 242, 242)
        Grid.ColumnHeadersDefaultCellStyle.ForeColor = Color.FromArgb(32, 32, 32)
        Grid.ColumnHeadersDefaultCellStyle.SelectionBackColor = Color.FromArgb(217, 225, 242)
        Grid.ColumnHeadersDefaultCellStyle.SelectionForeColor = Color.FromArgb(20, 20, 20)
        Grid.ColumnHeadersDefaultCellStyle.Alignment = System.Windows.Forms.DataGridViewContentAlignment.MiddleCenter
        Grid.ColumnHeadersDefaultCellStyle.WrapMode = System.Windows.Forms.DataGridViewTriState.True
        Grid.ColumnHeadersDefaultCellStyle.Font = New Font("Segoe UI Semibold", 9.0F, FontStyle.Bold)
        Grid.ColumnHeadersHeight = 52
        Grid.ColumnHeadersHeightSizeMode = System.Windows.Forms.DataGridViewColumnHeadersHeightSizeMode.DisableResizing
        Grid.DefaultCellStyle.BackColor = Color.White
        Grid.DefaultCellStyle.ForeColor = Color.FromArgb(45, 58, 64)
        Grid.DefaultCellStyle.SelectionBackColor = Color.FromArgb(217, 225, 242)
        Grid.DefaultCellStyle.SelectionForeColor = Color.FromArgb(20, 20, 20)
        Grid.DefaultCellStyle.Padding = New System.Windows.Forms.Padding(3, 0, 3, 0)
        Grid.AlternatingRowsDefaultCellStyle.BackColor = Color.White
        Grid.GridColor = Color.FromArgb(208, 208, 208)
        Grid.EditMode = System.Windows.Forms.DataGridViewEditMode.EditOnKeystrokeOrF2
        AddHandler Grid.CellMouseDown, AddressOf GridCellMouseDown
        AddHandler Grid.CellMouseDoubleClick, AddressOf GridCellMouseDoubleClick
        AddHandler Grid.CellClick, AddressOf GridCellClick
        AddHandler Grid.CellDoubleClick, AddressOf GridCellDoubleClick
        AddHandler Grid.SelectionChanged, AddressOf GridSelectionChanged
        AddHandler Grid.CellBeginEdit, AddressOf GridCellBeginEdit
        AddHandler Grid.CellEndEdit, AddressOf GridCellEndEdit
        AddHandler Grid.DataError, AddressOf GridDataError
        AddHandler Grid.KeyDown, AddressOf GridKeyDown
        AddHandler Grid.ColumnDisplayIndexChanged, AddressOf GridLayoutChanged
        AddHandler Grid.ColumnWidthChanged, AddressOf GridLayoutChanged
        AddHandler Grid.RowPostPaint, AddressOf GridRowPostPaint
        AddHandler Grid.ColumnHeaderMouseClick, AddressOf GridColumnHeaderMouseClick
        AddHandler Grid.RowHeaderMouseClick, AddressOf GridRowHeaderMouseClick
        AddHandler Grid.CellValueChanged, AddressOf GridCellValueChangedForFormula
        AddHandler Grid.CellPainting, AddressOf GridExcelCellPainting
        AddHandler Grid.MouseMove, AddressOf GridFillHandleMouseMove
        AddHandler Grid.MouseUp, AddressOf GridFillHandleMouseUp
        AddHandler Grid.Scroll, AddressOf GridScrolledForLazyFeatures
        MainSplit = New System.Windows.Forms.SplitContainer()
        MainSplit.Dock = DockStyle.Fill
        MainSplit.Orientation = System.Windows.Forms.Orientation.Vertical
        MainSplit.SplitterWidth = 5
        MainSplit.Panel1MinSize = 0
        MainSplit.Panel2MinSize = 0
        'Không gán SplitterDistance khi Form chưa hoàn tất Layout.
        'Kích thước SplitContainer tại thời điểm này có thể bằng 0 và gây lỗi runtime.
        MainSplit.Panel1.Controls.Add(Grid)
        BuildPreviewPanel()
        MainSplit.Panel2.Controls.Add(PreviewPanel)
        MainSplit.Panel2Collapsed = False
        root.Controls.Add(MainSplit, 0, 3)

        BuildStatusBar()
        root.Controls.Add(StatusBar, 0, 4)
        BuildContextMenu()

        AddHandler Me.Shown, AddressOf BomViewerFormShown
        AddHandler Me.Resize, AddressOf BomViewerFormResized
        AddHandler Me.FormClosed, AddressOf BomViewerFormClosed

        _inventorSyncTimer = New System.Windows.Forms.Timer()
        _inventorSyncTimer.Interval = 500
        AddHandler _inventorSyncTimer.Tick, AddressOf InventorSyncTimerTick
        _inventorSyncTimer.Start()

        'Không tạo Selection Highlight Timer; Highlight chỉ chạy khi user nhấn nút HIGHLIGHT/ZOOM hoặc phím tắt.
        _selectionTimer = Nothing

        _searchTimer = New System.Windows.Forms.Timer()
        _searchTimer.Interval = 280
        AddHandler _searchTimer.Tick, AddressOf SearchTimerTick
    End Sub

    Private Sub BomViewerFormShown(ByVal sender As Object, ByVal e As EventArgs)
        ApplyDefaultSplitterDistance()
    End Sub

    Private Sub BomViewerFormResized(ByVal sender As Object, ByVal e As EventArgs)
        If MainSplit Is Nothing Then Exit Sub
        If MainSplit.Panel2Collapsed Then Exit Sub
        SafeSetSplitterDistance(MainSplit, MainSplit.SplitterDistance)
    End Sub

    Private Sub ApplyDefaultSplitterDistance()
        If MainSplit Is Nothing Then Exit Sub
        If MainSplit.IsDisposed Then Exit Sub
        If MainSplit.Panel2Collapsed Then Exit Sub

        Dim desired As Integer = MainSplit.ClientSize.Width - 340
        SafeSetSplitterDistance(MainSplit, desired)
    End Sub

    Private Sub SafeSetSplitterDistance(ByVal target As System.Windows.Forms.SplitContainer, ByVal desired As Integer)
        If target Is Nothing OrElse target.IsDisposed Then Exit Sub
        If target.Orientation <> System.Windows.Forms.Orientation.Vertical Then Exit Sub

        Dim availableWidth As Integer = target.ClientSize.Width
        If availableWidth <= 0 Then Exit Sub

        Dim minimumValue As Integer = Math.Max(0, target.Panel1MinSize)
        Dim maximumValue As Integer = availableWidth - Math.Max(0, target.Panel2MinSize) - target.SplitterWidth

        'Nếu cửa sổ đang quá nhỏ, tạm thời không thay đổi vị trí thanh chia.
        If maximumValue < minimumValue Then Exit Sub

        Dim safeValue As Integer = desired
        If safeValue < minimumValue Then safeValue = minimumValue
        If safeValue > maximumValue Then safeValue = maximumValue

        Try
            target.SplitterDistance = safeValue
        Catch
            'Không để lỗi giao diện làm dừng quá trình xuất BOM.
        End Try
    End Sub

    Private Sub EnableGridDoubleBuffer(ByVal targetGrid As DataGridView)
        If targetGrid Is Nothing Then Exit Sub
        Try
            Dim propertyInfo As System.Reflection.PropertyInfo = GetType(DataGridView).GetProperty(
                "DoubleBuffered", _
                System.Reflection.BindingFlags.Instance Or System.Reflection.BindingFlags.NonPublic)
            If propertyInfo IsNot Nothing Then propertyInfo.SetValue(targetGrid, True, Nothing)
        Catch
        End Try
    End Sub


'####################################################################
' SUBSECTION 15.03 - RIBBON / QUICK ACCESS / TOOLBAR
'####################################################################

    Private Sub BuildRibbonHost()
        RibbonHost = New Panel()
        RibbonHost.Dock = DockStyle.Fill
        RibbonHost.BackColor = Color.FromArgb(242, 247, 250)
        RibbonHost.Padding = New System.Windows.Forms.Padding(0)

        RibbonQuickBar = New System.Windows.Forms.FlowLayoutPanel()
        RibbonQuickBar.Dock = DockStyle.Top
        RibbonQuickBar.Height = 30
        RibbonQuickBar.FlowDirection = System.Windows.Forms.FlowDirection.LeftToRight
        RibbonQuickBar.WrapContents = False
        RibbonQuickBar.Padding = New System.Windows.Forms.Padding(6, 2, 6, 2)
        RibbonQuickBar.BackColor = Color.FromArgb(225, 236, 242)
        RibbonHost.Controls.Add(RibbonQuickBar)

        AddQuickButton("REFRESH", AddressOf RefreshClicked, "Smart Refresh")
        AddQuickButton("REVIEW [0]", AddressOf ReviewPendingClicked, "Pending Changes Review")
        AddQuickButton("COMMIT", AddressOf CommitPendingClicked, "Commit Pending Changes")
        AddQuickButton("SAVE", AddressOf SaveChangedDocumentsClicked, "Save committed documents")
        AddQuickButton("UNDO", AddressOf UndoClicked, "Undo")
        AddQuickButton("REDO", AddressOf RedoClicked, "Redo")
        AddQuickButton("SAFE MODE", AddressOf ToggleSafeModeClicked, "Read Only safety mode")

        RibbonCollapseButton = New Button()
        RibbonCollapseButton.Text = "THU GỌN ▲"
        RibbonCollapseButton.AutoSize = False
        RibbonCollapseButton.Size = New Size(92, 24)
        RibbonCollapseButton.FlatStyle = FlatStyle.Flat
        RibbonCollapseButton.FlatAppearance.BorderSize = 0
        RibbonCollapseButton.BackColor = Color.FromArgb(225, 236, 242)
        RibbonCollapseButton.ForeColor = Color.FromArgb(35, 85, 105)
        RibbonCollapseButton.Font = New Font("Segoe UI", 8.0F, FontStyle.Bold)
        AddHandler RibbonCollapseButton.Click, AddressOf ToggleRibbonCollapsed
        RibbonQuickBar.Controls.Add(RibbonCollapseButton)

        RibbonTabBar = New System.Windows.Forms.FlowLayoutPanel()
        RibbonTabBar.Dock = DockStyle.Top
        RibbonTabBar.Height = 30
        RibbonTabBar.FlowDirection = System.Windows.Forms.FlowDirection.LeftToRight
        RibbonTabBar.WrapContents = False
        RibbonTabBar.Padding = New System.Windows.Forms.Padding(4, 1, 4, 1)
        RibbonTabBar.BackColor = Color.White
        RibbonHost.Controls.Add(RibbonTabBar)
        RibbonTabBar.BringToFront()

        Dim tabs() As String = {"HOME", "BOM", "STRUCTURE", "CHECK", "DRAWINGS", "CHANGES", "MANUFACTURING", "TOOLS"}
        For Each tabName As String In tabs
            AddRibbonTabButton(tabName)
        Next

        RibbonContent = New Panel()
        RibbonContent.Dock = DockStyle.Fill
        RibbonContent.BackColor = Color.FromArgb(248, 250, 252)
        RibbonContent.Padding = New System.Windows.Forms.Padding(0)
        RibbonHost.Controls.Add(RibbonContent)
        RibbonContent.BringToFront()

        BuildToolBar()
        UpdateRibbonTabVisuals()
    End Sub

    Private Sub AddQuickButton(ByVal caption As String, ByVal handler As EventHandler, ByVal tip As String)
        Dim button As New Button()
        button.Text = caption
        button.AutoSize = False
        Dim quickText As Size = System.Windows.Forms.TextRenderer.MeasureText(caption, New Font("Segoe UI", 8.0F, FontStyle.Bold))
        button.Size = New Size(Math.Max(64, Math.Min(118, quickText.Width + 20)), 24)
        button.Margin = New System.Windows.Forms.Padding(2, 0, 2, 0)
        button.FlatStyle = FlatStyle.Flat
        button.FlatAppearance.BorderSize = 0
        button.BackColor = Color.FromArgb(225, 236, 242)
        button.ForeColor = Color.FromArgb(40, 70, 85)
        button.Font = New Font("Segoe UI", 8.0F, FontStyle.Bold)
        Dim tipControl As New System.Windows.Forms.ToolTip()
        tipControl.SetToolTip(button, tip)
        AddHandler button.Click, handler
        RibbonQuickBar.Controls.Add(button)
        _quickButtons(caption.Split("["c)(0).Trim()) = button
    End Sub

    Private Sub AddRibbonTabButton(ByVal tabName As String)
        Dim button As New Button()
        button.Text = tabName
        button.Tag = tabName
        button.AutoSize = False
        Dim tabText As Size = System.Windows.Forms.TextRenderer.MeasureText(tabName, New Font("Segoe UI", 8.5F, FontStyle.Bold))
        button.Size = New Size(Math.Max(82, Math.Min(150, tabText.Width + 30)), 27)
        button.Margin = New System.Windows.Forms.Padding(1, 0, 1, 0)
        button.FlatStyle = FlatStyle.Flat
        button.FlatAppearance.BorderSize = 0
        button.Font = New Font("Segoe UI", 8.5F, FontStyle.Bold)
        AddHandler button.Click, AddressOf RibbonTabClicked
        RibbonTabBar.Controls.Add(button)
        _ribbonTabButtons(tabName) = button
    End Sub

    Private Sub RibbonTabClicked(ByVal sender As Object, ByVal e As EventArgs)
        Dim button As Button = TryCast(sender, Button)
        If button Is Nothing Then Exit Sub
        Dim requestedTab As String = Convert.ToString(button.Tag)
        If String.IsNullOrWhiteSpace(requestedTab) Then Exit Sub

        If _ribbonCollapsed AndAlso String.Equals(_activeRibbonTab, requestedTab, StringComparison.OrdinalIgnoreCase) Then
            _ribbonCollapsed = False
        Else
            _activeRibbonTab = requestedTab
            _ribbonCollapsed = False
        End If

        ApplyRibbonCollapsedState()
        BuildToolBar()
        UpdateRibbonTabVisuals()
        UpdatePreviewFromCurrentRow()
    End Sub

    Private Sub ToggleRibbonCollapsed(ByVal sender As Object, ByVal e As EventArgs)
        _ribbonCollapsed = Not _ribbonCollapsed
        ApplyRibbonCollapsedState()
    End Sub

    Private Sub ApplyRibbonCollapsedState()
        If RibbonContent Is Nothing OrElse RibbonHost Is Nothing Then Exit Sub
        RibbonContent.Visible = Not _ribbonCollapsed
        RibbonCollapseButton.Text = If(_ribbonCollapsed, "MỞ RỘNG ▼", "THU GỌN ▲")
        RibbonHost.Height = If(_ribbonCollapsed, 62, 128)
        If MainLayout IsNot Nothing AndAlso MainLayout.RowStyles.Count > 0 Then
            MainLayout.RowStyles(0).Height = If(_ribbonCollapsed, 62.0F, 136.0F)
        End If
    End Sub

    Private Sub UpdateRibbonTabVisuals()
        For Each pair As KeyValuePair(Of String, Button) In _ribbonTabButtons
            Dim active As Boolean = String.Equals(pair.Key, _activeRibbonTab, StringComparison.OrdinalIgnoreCase)
            pair.Value.BackColor = If(active, Color.FromArgb(210, 235, 243), Color.White)
            pair.Value.ForeColor = If(active, Color.FromArgb(20, 95, 120), Color.FromArgb(65, 75, 82))
            pair.Value.FlatAppearance.BorderSize = If(active, 1, 0)
            pair.Value.FlatAppearance.BorderColor = Color.FromArgb(85, 155, 175)
        Next
    End Sub

    Private Sub RegisterUiCommands()
        BomCommandRegistry.Clear()

        ' HOME
        RegisterCommand("LoadBom", "Load BOM", "LOAD BOM", "HOME", "PROJECT", "LOAD", "Load active Inventor Assembly.", "", False, False, False, 10, True, AddressOf LoadBomClicked)
        RegisterCommand("SmartRefresh", "Smart Refresh", "REFRESH", "HOME", "PROJECT", "REFRESH", "Incremental refresh.", "F5", False, False, False, 20, True, AddressOf RefreshClicked)
        RegisterCommand("FullRefresh", "Full Refresh", "FULL REFRESH", "HOME", "PROJECT", "FULL REFRESH", "Full reload: Shift+F5.", "Shift+F5", False, False, False, 30, False, AddressOf RefreshClicked)
        RegisterCommand("ReviewPending", "Review Pending", "REVIEW", "HOME", "TRANSACTION", "REVIEW", "Review staged changes.", "", False, False, False, 10, False, AddressOf ReviewPendingClicked)
        RegisterCommand("CommitAll", "Commit", "COMMIT", "HOME", "TRANSACTION", "COMMIT", "Commit all pending changes.", "Ctrl+Enter", True, False, False, 20, True, AddressOf CommitPendingClicked)
        RegisterCommand("Save", "Save", "SAVE", "HOME", "TRANSACTION", "SAVE", "Save committed documents.", "Ctrl+S", True, False, False, 30, False, AddressOf SaveChangedDocumentsClicked)
        RegisterCommand("Undo", "Undo", "UNDO", "HOME", "TRANSACTION", "UNDO", "Undo last transaction/edit.", "Ctrl+Z", True, False, False, 40, False, AddressOf UndoClicked)
        RegisterCommand("Redo", "Redo", "REDO", "HOME", "TRANSACTION", "REDO", "Redo.", "Ctrl+Y", True, False, False, 50, False, AddressOf RedoClicked)
        RegisterCommand("Dashboard", "Dashboard", "DASHBOARD", "HOME", "SUMMARY", "DASHBOARD", "Actionable project dashboard.", "", False, False, False, 10, False, AddressOf DashboardClicked)
        RegisterCommand("ProjectHealth", "Project Health", "HEALTH", "HOME", "SUMMARY", "HEALTH", "Project health and integrity summary.", "", False, False, False, 20, False, AddressOf HealthCheckClicked)

        ' BOM
        RegisterCommand("AddProperty", "Add iProperty", "ADD PROPERTY", "BOM", "EDIT", "IPROPERTY", "Add iProperty columns.", "", True, False, False, 10, True, AddressOf AddPropertiesClicked)
        RegisterCommand("EditProperty", "Edit", "EDIT", "BOM", "EDIT", "EDIT", "Edit selected property.", "", True, False, True, 20, False, AddressOf BeginEditPropertyClicked)
        RegisterCommand("ClearProperty", "Clear", "CLEAR", "BOM", "EDIT", "CLEAR", "Clear selected property.", "", True, True, True, 30, False, AddressOf ClearSelectedCellsClicked)
        RegisterCommand("CopyCell", "Copy Cell", "COPY CELL", "BOM", "CLIPBOARD", "COPY", "Copy current cell.", "Ctrl+C", False, False, False, 10, False, AddressOf CopyCurrentCellClicked)
        RegisterCommand("CopyRange", "Copy Range", "COPY RANGE", "BOM", "CLIPBOARD", "COPY", "Copy selected range.", "", False, False, False, 20, False, AddressOf CopySelectedCellsClicked)
        RegisterCommand("Paste", "Paste", "PASTE", "BOM", "CLIPBOARD", "PASTE", "Paste into editable properties.", "Ctrl+V", True, False, False, 30, False, AddressOf PasteCellsClicked)
        RegisterCommand("FillDown", "Fill Down", "FILL DOWN", "BOM", "CLIPBOARD", "FILL", "Fill selected cells down.", "", True, False, False, 40, False, AddressOf FillDownClicked)
        RegisterCommand("ColumnManager", "Column Manager", "COLUMNS", "BOM", "DATA", "COLUMNS", "Manage visible columns.", "", False, False, False, 10, True, AddressOf ManageColumnsClicked)
        RegisterCommand("Units", "Units", "UNITS", "BOM", "DATA", "UNITS", "Display/export units.", "", False, False, False, 20, False, AddressOf UnitManagerClicked)
        RegisterCommand("FeatureManager", "Feature Manager", "FEATURES", "BOM", "DATA", "FEATURE", "Lazy-load feature manager.", "", False, False, False, 30, False, AddressOf FeatureManagerClicked)
        RegisterCommand("Thumbnail", "Thumbnail", "THUMBNAIL", "BOM", "VIEW", "DRAWING", "Toggle thumbnail/detail panel.", "", False, False, False, 10, False, AddressOf ToggleThumbnailFeatureClicked)
        RegisterCommand("CommitSelected", "Commit Selected", "COMMIT SEL", "BOM", "TRANSACTION", "COMMIT", "Commit selected changes.", "", True, False, True, 10, False, AddressOf CommitSelectedClicked)
        RegisterCommand("DiscardSelected", "Discard Selected", "DISCARD SEL", "BOM", "TRANSACTION", "CLEAR", "Discard selected staged changes.", "", True, True, True, 20, False, AddressOf ReviewPendingClicked)

        ' STRUCTURE
        RegisterCommand("DisplayMode", "Display Mode", "DISPLAY MODE", "STRUCTURE", "DISPLAY", "STRUCTURE", "Parts Only / Structured / Hybrid.", "", False, False, False, 10, True, Nothing)
        RegisterCommand("ExpandAll", "Expand All", "EXPAND ALL", "STRUCTURE", "TREE", "EXPAND", "Expand assembly tree.", "", False, False, False, 10, False, AddressOf ExpandAllGroupsClicked)
        RegisterCommand("CollapseAll", "Collapse All", "COLLAPSE ALL", "STRUCTURE", "TREE", "COLLAPSE", "Collapse assembly tree.", "", False, False, False, 20, False, AddressOf CollapseAllGroupsClicked)
        RegisterCommand("WhereUsed", "Where Used", "WHERE USED", "STRUCTURE", "DEPENDENCY", "WHERE USED", "Dependency tree.", "", False, False, True, 10, True, AddressOf WhereUsedClicked)
        RegisterCommand("Impact", "Impact", "IMPACT", "STRUCTURE", "DEPENDENCY", "IMPACT", "Impact analysis.", "", False, False, True, 20, True, AddressOf ImpactAnalysisClicked)
        RegisterCommand("Highlight", "Highlight", "HIGHLIGHT", "STRUCTURE", "VIEW", "HIGHLIGHT", "Highlight selected occurrence.", "", False, False, True, 10, False, AddressOf HighlightClicked)
        RegisterCommand("Zoom", "Zoom", "ZOOM", "STRUCTURE", "VIEW", "ZOOM", "Zoom selected occurrence.", "", False, False, True, 20, False, AddressOf ZoomClicked)
        RegisterCommand("Isolate", "Isolate", "ISOLATE", "STRUCTURE", "VIEW", "ISOLATE", "Isolate selected occurrences.", "", True, False, True, 30, False, AddressOf IsolateOccurrencesClicked)
        RegisterCommand("Restore", "Restore", "RESTORE", "STRUCTURE", "VIEW", "RESTORE", "Restore visibility.", "", True, False, False, 40, False, AddressOf RestoreIsolationClicked)
        RegisterCommand("Visibility", "Visibility", "VISIBILITY", "STRUCTURE", "MODEL", "VISIBILITY", "Toggle visibility.", "", True, False, True, 10, False, AddressOf ToggleOccurrenceVisibilityClicked)
        RegisterCommand("Suppress", "Suppress", "SUPPRESS", "STRUCTURE", "MODEL", "SUPPRESS", "Suppress occurrence.", "", True, True, True, 20, False, AddressOf SuppressOccurrencesClicked)
        RegisterCommand("Unsuppress", "Unsuppress", "UNSUPPRESS", "STRUCTURE", "MODEL", "UNSUPPRESS", "Unsuppress occurrence.", "", True, False, True, 30, False, AddressOf UnsuppressOccurrencesClicked)
        RegisterCommand("Ground", "Ground / Unground", "GROUND", "STRUCTURE", "MODEL", "GROUND", "Ground/Unground occurrence.", "", True, False, True, 40, False, AddressOf ToggleGroundedClicked)

        ' CHECK - Quality only
        RegisterCommand("CheckProject", "Check Project", "CHECK PROJECT", "CHECK", "VALIDATION", "CHECK", "Run project quality checks.", "", False, False, False, 10, True, AddressOf ProjectCheckClicked)
        RegisterCommand("Validation", "Run Validation", "VALIDATION", "CHECK", "VALIDATION", "VALIDATION", "Run validation engine.", "", False, False, False, 20, True, AddressOf ProjectCheckClicked)
        RegisterCommand("Integrity", "Integrity Check", "INTEGRITY", "CHECK", "INTEGRITY", "HEALTH", "Cache/structure/quantity integrity.", "", False, False, False, 10, False, AddressOf HealthCheckClicked)
        RegisterCommand("Regression", "Regression Test", "REGRESSION", "CHECK", "REGRESSION", "CHECK", "Final regression test.", "", False, False, False, 10, False, AddressOf FinalRegressionClicked)
        RegisterCommand("Health", "Health Check", "HEALTH", "CHECK", "HEALTH", "HEALTH", "System/project health.", "", False, False, False, 10, False, AddressOf HealthCheckClicked)

        ' DRAWINGS
        RegisterCommand("OpenPart", "Open Part", "OPEN PART", "DRAWINGS", "OPEN", "OPEN", "Open selected model.", "", False, False, True, 10, False, AddressOf OpenPartClicked)
        RegisterCommand("OpenDrawing", "Open Drawing", "OPEN DRAWING", "DRAWINGS", "OPEN", "DRAWING", "Open matching drawing.", "", False, False, True, 20, True, AddressOf OpenDrawingClicked)
        RegisterCommand("LocateDrawing", "Assign Drawing", "ASSIGN", "DRAWINGS", "OPEN", "LOCATE", "Assign/locate drawing.", "", False, False, True, 30, False, AddressOf LocateDrawingClicked)
        RegisterCommand("Mark", "Mark", "MARK", "DRAWINGS", "MARK", "MARK", "Mark selected rows.", "", False, False, True, 10, False, AddressOf ToggleMarkClicked)
        RegisterCommand("ClearMarks", "Clear Marks", "CLEAR MARKS", "DRAWINGS", "MARK", "CLEAR", "Clear marks.", "", False, False, False, 20, False, AddressOf ClearAllMarksClicked)

        ' CHANGES
        RegisterCommand("Snapshot", "Create Snapshot", "SNAPSHOT", "CHANGES", "SNAPSHOT", "SNAPSHOT", "Create BOM snapshot.", "", False, False, False, 10, True, AddressOf CaptureSnapshotClicked)
        RegisterCommand("Compare", "Compare", "COMPARE", "CHANGES", "COMPARE", "COMPARE", "Compare current BOM with snapshot.", "", False, False, False, 10, True, AddressOf CompareSnapshotClicked)
        RegisterCommand("ChangeImpact", "Impact Analysis", "IMPACT", "CHANGES", "ANALYSIS", "IMPACT", "Analyze change impact.", "", False, False, True, 10, False, AddressOf ImpactAnalysisClicked)
        RegisterCommand("ChangeReport", "Change Report", "CHANGE REPORT", "CHANGES", "REPORT", "REPORT", "Export engineering change report.", "", False, False, False, 10, False, AddressOf ChangeReportClicked)

        ' MANUFACTURING
        RegisterCommand("MfgDashboard", "Manufacturing Dashboard", "DASHBOARD", "MANUFACTURING", "SUMMARY", "DASHBOARD", "Manufacturing summary.", "", False, False, False, 10, True, AddressOf ManufacturingSummaryClicked)
        RegisterCommand("Plate", "Plate", "PLATE", "MANUFACTURING", "FABRICATION", "PLATE", "Plate list.", "", False, False, False, 10, True, AddressOf ManufacturingPlateClicked)
        RegisterCommand("Profile", "Profile", "PROFILE", "MANUFACTURING", "FABRICATION", "PROFILE", "Profile cut list.", "", False, False, False, 20, False, AddressOf ManufacturingProfileClicked)
        RegisterCommand("Tube", "Tube / Pipe", "TUBE", "MANUFACTURING", "FABRICATION", "TUBE", "Tube/Pipe list.", "", False, False, False, 30, False, AddressOf ManufacturingTubeClicked)
        RegisterCommand("SheetMetal", "Sheet Metal", "SHEET METAL", "MANUFACTURING", "FABRICATION", "SHEET METAL", "Sheet metal list.", "", False, False, False, 40, False, AddressOf ManufacturingSheetMetalClicked)
        RegisterCommand("Purchased", "Purchased", "PURCHASED", "MANUFACTURING", "PURCHASING", "PURCHASED", "Purchased list.", "", False, False, False, 10, False, AddressOf ManufacturingPurchasedClicked)
        RegisterCommand("Fastener", "Fastener", "FASTENER", "MANUFACTURING", "PURCHASING", "FASTENER", "Fastener list.", "", False, False, False, 20, False, AddressOf ManufacturingFastenerClicked)
        RegisterCommand("MfgExport", "Manufacturing CSV", "MFG CSV", "MANUFACTURING", "EXPORT", "EXPORT", "Export manufacturing data.", "", False, False, False, 10, False, AddressOf ManufacturingExportClicked)

        ' TOOLS
        RegisterCommand("ColumnManagerTools", "Column Manager", "COLUMNS", "TOOLS", "LAYOUT", "COLUMNS", "Column manager.", "", False, False, False, 10, False, AddressOf ManageColumnsClicked)
        RegisterCommand("SaveLayout", "Save Layout", "SAVE LAYOUT", "TOOLS", "LAYOUT", "SAVE", "Save UI layout.", "", False, False, False, 20, False, AddressOf SaveLayoutClicked)
        RegisterCommand("LoadLayout", "Load Layout", "LOAD LAYOUT", "TOOLS", "LAYOUT", "LOAD", "Load UI layout.", "", False, False, False, 30, False, AddressOf LoadLayoutClicked)
        RegisterCommand("ScanMode", "Scan Mode", "SCAN MODE", "TOOLS", "PERFORMANCE", "SCAN", "FAST/NORMAL/DEEP.", "", False, False, False, 10, True, AddressOf ScanModeClicked)
        RegisterCommand("Profiler", "Profiler", "PROFILER", "TOOLS", "PERFORMANCE", "PROFILER", "Performance profiler.", "", False, False, False, 20, False, AddressOf CacheInfoClicked)
        RegisterCommand("ClearGeometry", "Clear Geometry", "CLEAR GEO", "TOOLS", "CACHE", "CACHE", "Clear geometry cache.", "", False, False, False, 10, False, AddressOf ClearGeometryCacheClicked)
        RegisterCommand("ClearThumbnail", "Clear Thumbnail", "CLEAR IMAGE", "TOOLS", "CACHE", "CACHE", "Clear thumbnail cache.", "", False, False, False, 20, False, AddressOf ClearThumbnailCacheClicked)
        RegisterCommand("ResetCounter", "Reset Counters", "RESET", "TOOLS", "CACHE", "RESET", "Reset performance counters.", "", False, False, False, 30, False, AddressOf ResetPerformanceCountersClicked)
        RegisterCommand("UpdateInventor", "Update", "UPDATE", "TOOLS", "INVENTOR", "UPDATE", "Inventor Update.", "", True, False, False, 10, False, AddressOf InventorUpdateClicked)
        RegisterCommand("RebuildInventor", "Rebuild", "REBUILD", "TOOLS", "INVENTOR", "REBUILD", "Inventor Rebuild.", "", True, False, False, 20, False, AddressOf InventorRebuildClicked)
        RegisterCommand("SaveAll", "Save All", "SAVE ALL", "TOOLS", "INVENTOR", "SAVE", "Save all open documents.", "", True, False, False, 30, False, AddressOf InventorSaveAllClicked)
        RegisterCommand("Commands", "Command Palette", "COMMANDS", "TOOLS", "SYSTEM", "COMMAND", "Search commands.", "Ctrl+Shift+P", False, False, False, 10, True, AddressOf CommandPaletteClicked)
        RegisterCommand("RecoverUi", "Recover UI", "RECOVER UI", "TOOLS", "SYSTEM", "RECOVERY", "Recover UI/layout.", "", False, False, False, 20, False, AddressOf RecoverUiClicked)
    End Sub

    Private Sub ConfigureCommandUiMetadata()
        Dim quickIds() As String = {"SmartRefresh", "ReviewPending", "CommitAll", "Save", "Undo", "Redo"}
        For Each id As String In quickIds
            Dim c As BomCommandDefinition = BomCommandRegistry.GetCommand(id)
            If c IsNot Nothing Then c.IsQuickAccess = True
        Next
        SetContext("OpenPart", "PART", "OPEN")
        SetContext("OpenDrawing", "PART", "OPEN")
        SetContext("Highlight", "PART", "VIEW")
        SetContext("Zoom", "PART", "VIEW")
        SetContext("Isolate", "PART", "VIEW")
        SetContext("Restore", "PART", "VIEW")
        SetContext("WhereUsed", "PART", "ANALYZE")
        SetContext("Impact", "PART", "ANALYZE")
        SetContext("EditProperty", "PART", "EDIT")
        SetContext("CopyCell", "PART", "GRID")
        SetContext("Paste", "PART", "GRID")
        SetContext("FillDown", "PART", "GRID")
        SetContext("ClearProperty", "PART", "GRID")
        SetContext("Visibility", "PART", "INVENTOR")
        SetContext("Suppress", "PART", "INVENTOR")
        SetContext("Unsuppress", "PART", "INVENTOR")
        SetContext("Ground", "PART", "INVENTOR")
    End Sub

    Private Sub SetContext(ByVal id As String, ByVal target As String, ByVal groupName As String)
        Dim c As BomCommandDefinition = BomCommandRegistry.GetCommand(id)
        If c Is Nothing Then Exit Sub
        c.ContextTarget = target : c.ContextGroup = groupName
        ConfigureCommandUiMetadata()
    End Sub

    Private Sub RegisterCommand(ByVal id As String, ByVal caption As String, ByVal shortCaption As String,
                                ByVal workspace As String, ByVal groupName As String, ByVal iconKey As String,
                                ByVal tooltip As String, ByVal shortcut As String, ByVal isWrite As Boolean,
                                ByVal destructive As Boolean, ByVal requiresSelection As Boolean,
                                ByVal orderValue As Integer, ByVal primary As Boolean, ByVal handler As EventHandler)
        Dim c As New BomCommandDefinition()
        c.Id = id : c.Caption = caption : c.ShortCaption = shortCaption
        c.Workspace = workspace : c.GroupName = groupName : c.IconKey = iconKey
        c.Tooltip = tooltip : c.Description = tooltip : c.Shortcut = shortcut
        c.IsWriteOperation = isWrite : c.IsDestructive = destructive
        c.RequiresSelection = requiresSelection : c.Order = orderValue
        c.IsPrimary = primary : c.Handler = handler
        c.CommandType = If(destructive, BomCommandType.DestructiveCommand, If(isWrite, BomCommandType.WriteCommand, BomCommandType.ReadOnlyCommand))
        BomCommandRegistry.Register(c)
    End Sub

    Private Sub BuildToolBar()
        If RibbonContent Is Nothing Then Exit Sub
        RibbonContent.SuspendLayout()
        Try
            If ToolBar IsNot Nothing Then
                RibbonContent.Controls.Remove(ToolBar)
                ToolBar.Dispose()
            End If
            ToolBar = New System.Windows.Forms.ToolStrip()
            ToolBar.Dock = DockStyle.Fill
            ToolBar.GripStyle = System.Windows.Forms.ToolStripGripStyle.Hidden
            ToolBar.RenderMode = System.Windows.Forms.ToolStripRenderMode.Professional
            ToolBar.BackColor = Color.FromArgb(248, 250, 252)
            ToolBar.ForeColor = Color.FromArgb(40, 55, 65)
            ToolBar.Padding = New System.Windows.Forms.Padding(8, 2, 8, 2)
            ToolBar.AutoSize = False
            ToolBar.Height = 68
            ToolBar.CanOverflow = True
            ToolBar.ShowItemToolTips = True
            ToolBar.ImageScalingSize = New Size(28, 28)
            RibbonContent.Controls.Add(ToolBar)

            Dim commands As List(Of BomCommandDefinition) = BomCommandRegistry.ForWorkspace(_activeRibbonTab)
            Dim lastGroup As String = ""
            For Each cmd As BomCommandDefinition In commands
                If Not String.Equals(lastGroup, cmd.GroupName, StringComparison.OrdinalIgnoreCase) Then
                    If lastGroup <> "" Then AddRibbonSeparator()
                    AddToolGroup(cmd.GroupName)
                    lastGroup = cmd.GroupName
                End If
                If cmd.Id = "DisplayMode" Then
                    AddDisplayModeButton()
                ElseIf cmd.Handler IsNot Nothing Then
                    AddRegisteredToolButton(cmd)
                End If
            Next
            ApplyCommandAvailability()
        Finally
            RibbonContent.ResumeLayout(True)
        End Try
    End Sub

    Private Sub AddRegisteredToolButton(ByVal cmd As BomCommandDefinition)
        Dim button As New System.Windows.Forms.ToolStripButton(cmd.ShortCaption)
        button.Name = "CMD_" & cmd.Id
        button.Tag = cmd
        button.DisplayStyle = System.Windows.Forms.ToolStripItemDisplayStyle.ImageAndText
        button.TextImageRelation = System.Windows.Forms.TextImageRelation.ImageAboveText
        button.Image = BomIconCache.GetOrCreate(cmd.IconKey, Function() CreateToolbarIcon(cmd.IconKey))
        button.ImageScaling = System.Windows.Forms.ToolStripItemImageScaling.None
        button.AutoSize = False
        button.Size = GetToolbarButtonSize(cmd.ShortCaption)
        button.Margin = New System.Windows.Forms.Padding(3, 1, 3, 1)
        button.Padding = New System.Windows.Forms.Padding(3, 2, 3, 2)
        button.Font = New Font("Segoe UI", 8.0F, If(cmd.IsPrimary, FontStyle.Bold, FontStyle.Regular))
        button.ToolTipText = cmd.Tooltip & If(String.IsNullOrWhiteSpace(cmd.Shortcut), "", "  [" & cmd.Shortcut & "]")
        button.AutoToolTip = True
        button.BackColor = If(cmd.IsPrimary, Color.FromArgb(225, 239, 248), Color.FromArgb(248, 250, 252))
        button.ForeColor = If(cmd.IsDestructive, Color.FromArgb(170, 55, 55), Color.FromArgb(45, 65, 78))
        AddHandler button.MouseEnter, AddressOf RibbonButtonMouseEnter
        AddHandler button.MouseLeave, AddressOf RibbonButtonMouseLeave
        AddHandler button.Click, cmd.Handler
        ToolBar.Items.Add(button)
    End Sub

    Private Sub ApplyCommandAvailability()
        If ToolBar Is Nothing Then Exit Sub
        For Each item As System.Windows.Forms.ToolStripItem In ToolBar.Items
            Dim cmd As BomCommandDefinition = TryCast(item.Tag, BomCommandDefinition)
            If cmd Is Nothing Then Continue For
            Dim enabled As Boolean = True
            If _safeMode AndAlso cmd.IsWriteOperation Then enabled = False
            If cmd.RequiresSelection AndAlso (Grid Is Nothing OrElse Grid.SelectedRows.Count = 0) Then enabled = False
            item.Enabled = enabled
        Next
    End Sub

    Private Sub AddRibbonSeparator()
        Dim separator As New System.Windows.Forms.ToolStripSeparator()
        separator.Margin = New System.Windows.Forms.Padding(6, 4, 6, 4)
        ToolBar.Items.Add(separator)
    End Sub

    Private Sub AddDisplayModeButton()
        _displayModeButton = New System.Windows.Forms.ToolStripButton("HYBRID BOM")
        _displayModeButton.DisplayStyle = System.Windows.Forms.ToolStripItemDisplayStyle.ImageAndText
        _displayModeButton.TextImageRelation = System.Windows.Forms.TextImageRelation.ImageAboveText
        _displayModeButton.Image = CreateToolbarIcon("THEO ASSEMBLY")
        _displayModeButton.ImageScaling = System.Windows.Forms.ToolStripItemImageScaling.None
        _displayModeButton.AutoSize = False
        _displayModeButton.Size = New Size(92, 58)
        _displayModeButton.Margin = New System.Windows.Forms.Padding(3, 1, 3, 1)
        _displayModeButton.Padding = New System.Windows.Forms.Padding(3, 2, 3, 2)
        _displayModeButton.Font = New Font("Segoe UI", 8.0F, FontStyle.Bold)
        _displayModeButton.BackColor = Color.FromArgb(220, 244, 247)
        _displayModeButton.ForeColor = Color.FromArgb(25, 100, 112)
        _displayModeButton.ToolTipText = "3 chế độ BOM: PARTS ONLY → STRUCTURED → HYBRID. Nhấn để chuyển chế độ."
        _displayModeButton.AutoToolTip = True
        AddHandler _displayModeButton.Click, AddressOf ToggleDisplayModeClicked
        ToolBar.Items.Add(_displayModeButton)
    End Sub

    Private Sub AddToolGroup(ByVal caption As String)
        Dim groupLabel As New System.Windows.Forms.ToolStripLabel(caption)
        groupLabel.Font = New Font("Segoe UI", 7.5F, FontStyle.Bold)
        groupLabel.ForeColor = Color.FromArgb(105, 115, 125)
        groupLabel.Margin = New System.Windows.Forms.Padding(5, 1, 1, 1)
        groupLabel.Alignment = System.Windows.Forms.ToolStripItemAlignment.Left
        groupLabel.ToolTipText = "Nhóm chức năng " & caption
        groupLabel.DisplayStyle = System.Windows.Forms.ToolStripItemDisplayStyle.Text
        ToolBar.Items.Add(groupLabel)
    End Sub

    Private Sub AddToolButton(ByVal caption As String, ByVal handler As EventHandler, ByVal description As String, ByVal isPrimary As Boolean)
        Dim button As New System.Windows.Forms.ToolStripButton(caption)
        button.DisplayStyle = System.Windows.Forms.ToolStripItemDisplayStyle.ImageAndText
        button.TextImageRelation = System.Windows.Forms.TextImageRelation.ImageAboveText
        button.Image = BomIconCache.GetOrCreate(caption, Function() CreateToolbarIcon(caption))
        button.ImageScaling = System.Windows.Forms.ToolStripItemImageScaling.None
        button.AutoSize = False
        button.Size = GetToolbarButtonSize(caption)
        button.Margin = New System.Windows.Forms.Padding(3, 1, 3, 1)
        button.Padding = New System.Windows.Forms.Padding(3, 2, 3, 2)
        button.Font = New Font("Segoe UI", 8.0F, FontStyle.Bold)
        button.ToolTipText = description
        button.AutoToolTip = True
        If isPrimary Then
            button.BackColor = Color.FromArgb(225, 239, 248)
            button.ForeColor = Color.FromArgb(25, 86, 125)
        Else
            button.BackColor = Color.FromArgb(248, 250, 252)
            button.ForeColor = Color.FromArgb(45, 65, 78)
        End If
        AddHandler button.MouseEnter, AddressOf RibbonButtonMouseEnter
        AddHandler button.MouseLeave, AddressOf RibbonButtonMouseLeave
        AddHandler button.Click, handler
        ToolBar.Items.Add(button)
    End Sub

    Private Function GetToolbarButtonSize(ByVal caption As String) As Size
        Dim measured As Size = System.Windows.Forms.TextRenderer.MeasureText(If(caption, ""), New Font("Segoe UI", 8.0F, FontStyle.Bold))
        Dim width As Integer = measured.Width + 24
        width = Math.Max(82, Math.Min(138, width))
        Return New Size(width, 58)
    End Function

    Private Sub RibbonButtonMouseEnter(ByVal sender As Object, ByVal e As EventArgs)
        Dim item As System.Windows.Forms.ToolStripItem = TryCast(sender, System.Windows.Forms.ToolStripItem)
        If item Is Nothing Then Exit Sub
        item.BackColor = Color.FromArgb(215, 240, 246)
    End Sub

    Private Sub RibbonButtonMouseLeave(ByVal sender As Object, ByVal e As EventArgs)
        Dim item As System.Windows.Forms.ToolStripItem = TryCast(sender, System.Windows.Forms.ToolStripItem)
        If item Is Nothing Then Exit Sub
        If item Is _displayModeButton Then
            item.BackColor = Color.FromArgb(220, 244, 247)
        Else
            item.BackColor = Color.FromArgb(248, 250, 252)
        End If
    End Sub

    Private Function CreateToolbarIcon(ByVal caption As String) As System.Drawing.Image
        Dim bmp As New System.Drawing.Bitmap(34, 34)
        Using g As System.Drawing.Graphics = System.Drawing.Graphics.FromImage(bmp)
            g.SmoothingMode = System.Drawing.Drawing2D.SmoothingMode.AntiAlias
            g.Clear(Color.Transparent)

            Dim key As String = If(caption, "").ToUpperInvariant()
            Dim navy As Color = Color.FromArgb(38, 105, 145)
            Dim cyan As Color = Color.FromArgb(40, 165, 185)
            Dim green As Color = Color.FromArgb(45, 155, 95)
            Dim orange As Color = Color.FromArgb(235, 150, 45)
            Dim red As Color = Color.FromArgb(215, 70, 70)
            Dim gray As Color = Color.FromArgb(100, 115, 125)
            Dim purple As Color = Color.FromArgb(145, 85, 175)

            If key.Contains("LOAD") Then
                Using b As New System.Drawing.SolidBrush(Color.FromArgb(250, 190, 55))
                    g.FillRectangle(b, 3, 10, 25, 17)
                    g.FillRectangle(b, 6, 7, 10, 5)
                End Using
                Using p As New System.Drawing.Pen(green, 3)
                    g.DrawLine(p, 25, 29, 25, 18)
                    g.DrawLine(p, 20, 23, 25, 18)
                    g.DrawLine(p, 30, 23, 25, 18)
                End Using

            ElseIf key.Contains("LÀM MỚI") Then
                Using p As New System.Drawing.Pen(navy, 3)
                    g.DrawArc(p, 5, 5, 24, 24, 35, 280)
                    g.DrawLine(p, 26, 5, 29, 12)
                    g.DrawLine(p, 26, 5, 20, 8)
                End Using

            ElseIf key.Contains("XÓA") OrElse key.Contains("BỎ TẤT") Then
                Using p As New System.Drawing.Pen(red, 4)
                    g.DrawLine(p, 7, 7, 27, 27)
                    g.DrawLine(p, 27, 7, 7, 27)
                End Using

            ElseIf key.Contains("IPROPERTY") Then
                Using b As New System.Drawing.SolidBrush(purple)
                    g.FillEllipse(b, 5, 4, 22, 22)
                End Using
                Using f As New System.Drawing.Font("Segoe UI", 14.0F, FontStyle.Bold)
                    g.DrawString("i", f, System.Drawing.Brushes.White, 12, 3)
                End Using
                Using b As New System.Drawing.SolidBrush(green)
                    g.FillEllipse(b, 21, 20, 12, 12)
                End Using
                Using p As New System.Drawing.Pen(Color.White, 2)
                    g.DrawLine(p, 27, 22, 27, 30)
                    g.DrawLine(p, 23, 26, 31, 26)
                End Using

            ElseIf key.Contains("TÍNH TOÁN") OrElse key.Contains("CALCULATOR") Then
                Using p As New System.Drawing.Pen(navy, 2)
                    g.DrawRectangle(p, 5, 3, 24, 29)
                    g.DrawRectangle(p, 9, 7, 16, 6)
                    g.DrawLine(p, 9, 18, 25, 18)
                    g.DrawLine(p, 9, 24, 25, 24)
                    g.DrawLine(p, 14, 15, 14, 29)
                    g.DrawLine(p, 20, 15, 20, 29)
                End Using

            ElseIf key.Contains("LƯU") Then
                Using b As New System.Drawing.SolidBrush(navy)
                    g.FillRectangle(b, 5, 4, 24, 26)
                End Using
                Using b As New System.Drawing.SolidBrush(Color.White)
                    g.FillRectangle(b, 9, 6, 14, 8)
                    g.FillRectangle(b, 10, 19, 14, 9)
                End Using

            ElseIf key.Contains("COPY") Then
                Using p As New System.Drawing.Pen(navy, 2)
                    g.DrawRectangle(p, 10, 5, 18, 22)
                    g.DrawRectangle(p, 5, 10, 18, 20)
                End Using
            ElseIf key.Contains("PASTE") Then
                Using p As New System.Drawing.Pen(green, 2)
                    g.DrawRectangle(p, 7, 8, 20, 23)
                    g.DrawRectangle(p, 12, 3, 10, 7)
                End Using
            ElseIf key.Contains("FILL") Then
                Using p As New System.Drawing.Pen(navy, 2)
                    g.DrawRectangle(p, 7, 4, 20, 25)
                    g.DrawLine(p, 17, 10, 17, 25)
                    g.DrawLine(p, 12, 20, 17, 25)
                    g.DrawLine(p, 22, 20, 17, 25)
                End Using
            ElseIf key.Contains("XUẤT") Then
                Using b As New System.Drawing.SolidBrush(green)
                    g.FillRectangle(b, 5, 4, 21, 27)
                End Using
                Using f As New System.Drawing.Font("Segoe UI", 13.0F, FontStyle.Bold)
                    g.DrawString("X", f, System.Drawing.Brushes.White, 7, 8)
                End Using
                If key.Contains("LỌC") Then
                    Using b As New System.Drawing.SolidBrush(gray)
                        Dim pts() As System.Drawing.Point = {New System.Drawing.Point(20, 7), New System.Drawing.Point(33, 7), New System.Drawing.Point(28, 15), New System.Drawing.Point(28, 25), New System.Drawing.Point(25, 28), New System.Drawing.Point(25, 15)}
                        g.FillPolygon(b, pts)
                    End Using
                ElseIf key.Contains("CHỌN") Then
                    Using p As New System.Drawing.Pen(navy, 2)
                        g.DrawLine(p, 23, 22, 27, 27)
                        g.DrawLine(p, 27, 27, 33, 17)
                    End Using
                Else
                    Using p As New System.Drawing.Pen(navy, 2)
                        g.DrawLine(p, 26, 23, 31, 28)
                        g.DrawLine(p, 31, 28, 33, 24)
                    End Using
                End If

            ElseIf key.Contains("ASSEMBLY") OrElse key.Contains("HIỂN THỊ") Then
                Using p As New System.Drawing.Pen(cyan, 2)
                    g.DrawRectangle(p, 5, 5, 10, 10)
                    g.DrawRectangle(p, 19, 5, 10, 10)
                    g.DrawRectangle(p, 12, 20, 10, 10)
                    g.DrawLine(p, 10, 15, 17, 20)
                    g.DrawLine(p, 24, 15, 17, 20)
                End Using

            ElseIf key.Contains("THU GỌN") Then
                Using p As New System.Drawing.Pen(navy, 3)
                    g.DrawEllipse(p, 5, 5, 24, 24)
                    g.DrawLine(p, 10, 17, 24, 17)
                End Using

            ElseIf key.Contains("MỞ RỘNG") Then
                Using p As New System.Drawing.Pen(navy, 3)
                    g.DrawEllipse(p, 5, 5, 24, 24)
                    g.DrawLine(p, 10, 17, 24, 17)
                    g.DrawLine(p, 17, 10, 17, 24)
                End Using

            ElseIf key.Contains("CỘT") OrElse key.Contains("BỐ CỤC") Then
                Using p As New System.Drawing.Pen(gray, 2)
                    g.DrawRectangle(p, 4, 5, 26, 24)
                    g.DrawLine(p, 12, 5, 12, 29)
                    g.DrawLine(p, 21, 5, 21, 29)
                    g.DrawLine(p, 4, 13, 30, 13)
                End Using

            ElseIf key.Contains("DRAWING") Then
                Using p As New System.Drawing.Pen(navy, 2)
                    g.DrawRectangle(p, 6, 4, 21, 27)
                    g.DrawLine(p, 10, 11, 23, 11)
                    g.DrawLine(p, 10, 16, 23, 16)
                    g.DrawLine(p, 10, 21, 20, 21)
                End Using

            ElseIf key.Contains("MỞ PART") Then
                Using p As New System.Drawing.Pen(cyan, 2)
                    Dim pts() As System.Drawing.Point = {New System.Drawing.Point(17, 3), New System.Drawing.Point(29, 10), New System.Drawing.Point(29, 24), New System.Drawing.Point(17, 31), New System.Drawing.Point(5, 24), New System.Drawing.Point(5, 10)}
                    g.DrawPolygon(p, pts)
                    g.DrawLine(p, 5, 10, 17, 17)
                    g.DrawLine(p, 29, 10, 17, 17)
                    g.DrawLine(p, 17, 17, 17, 31)
                End Using

            ElseIf key.Contains("HIGHLIGHT") OrElse key.Contains("ĐÁNH DẤU") Then
                Using b As New System.Drawing.SolidBrush(Color.FromArgb(255, 225, 75))
                    g.FillEllipse(b, 6, 6, 22, 22)
                End Using
                Using p As New System.Drawing.Pen(orange, 2)
                    g.DrawEllipse(p, 6, 6, 22, 22)
                End Using

            ElseIf key.Contains("ZOOM") Then
                Using p As New System.Drawing.Pen(navy, 3)
                    g.DrawEllipse(p, 5, 5, 18, 18)
                    g.DrawLine(p, 21, 21, 30, 30)
                End Using

            Else
                Using b As New System.Drawing.SolidBrush(navy)
                    g.FillEllipse(b, 6, 6, 22, 22)
                End Using
                Using f As New System.Drawing.Font("Segoe UI", 11.0F, FontStyle.Bold)
                    g.DrawString("•", f, System.Drawing.Brushes.White, 11, 7)
                End Using
            End If
        End Using
        Return bmp
    End Function


'####################################################################
' SUBSECTION 15.04 - GRID PAINTING / STATUS BAR / CONTEXT MENU
'####################################################################

    Private Sub GridExcelCellPainting(ByVal sender As Object, ByVal e As System.Windows.Forms.DataGridViewCellPaintingEventArgs)
        If e.RowIndex = -1 AndAlso e.ColumnIndex = -1 Then
            e.PaintBackground(e.CellBounds, True)
            Using p As New System.Drawing.Pen(Color.FromArgb(150, 150, 150))
                e.Graphics.DrawLine(p, e.CellBounds.Right - 11, e.CellBounds.Bottom - 4, e.CellBounds.Right - 4, e.CellBounds.Bottom - 11)
            End Using
            e.Handled = True
            Exit Sub
        End If

        'Excel-like fill handle: vẽ ô vuông nhỏ ở góc phải-dưới của ô hiện hành có thể sửa.
        If e.RowIndex >= 0 AndAlso e.ColumnIndex >= 0 AndAlso Grid IsNot Nothing AndAlso Grid.CurrentCell IsNot Nothing Then
            If Grid.CurrentCell.RowIndex = e.RowIndex AndAlso Grid.CurrentCell.ColumnIndex = e.ColumnIndex Then
                Dim col As DataGridViewColumn = Grid.Columns(e.ColumnIndex)
                Dim item As PartBomItem = TryCast(Grid.Rows(e.RowIndex).Tag, PartBomItem)
                Dim pi As PropertyColumnInfo = TryCast(col.Tag, PropertyColumnInfo)
                If item IsNot Nothing AndAlso pi IsNot Nothing AndAlso Not col.ReadOnly Then
                    e.Paint(e.CellBounds, System.Windows.Forms.DataGridViewPaintParts.All)
                    Dim handleRect As New Rectangle(e.CellBounds.Right - FillHandleSize, e.CellBounds.Bottom - FillHandleSize, FillHandleSize - 1, FillHandleSize - 1)
                    Using b As New System.Drawing.SolidBrush(Color.FromArgb(45, 95, 120))
                        e.Graphics.FillRectangle(b, handleRect)
                    End Using
                    e.Handled = True
                End If
            End If
        End If
    End Sub

    Private Sub BuildStatusBar()
        StatusBar = New System.Windows.Forms.StatusStrip()
        StatusBar.Dock = DockStyle.Fill
        StatusBar.SizingGrip = True
        StatusBar.BackColor = Color.FromArgb(229, 241, 245)
        StatusBar.ForeColor = Color.FromArgb(55, 80, 90)

        StatusAssembly = New System.Windows.Forms.ToolStripStatusLabel()
        StatusAssembly.Spring = True
        StatusAssembly.TextAlign = System.Drawing.ContentAlignment.MiddleLeft
        StatusParts = New System.Windows.Forms.ToolStripStatusLabel()
        StatusVisible = New System.Windows.Forms.ToolStripStatusLabel()
        StatusQty = New System.Windows.Forms.ToolStripStatusLabel()
        StatusDrawing = New System.Windows.Forms.ToolStripStatusLabel()
        StatusLoadTime = New System.Windows.Forms.ToolStripStatusLabel()
        StatusSelection = New System.Windows.Forms.ToolStripStatusLabel()
        StatusSelection.Text = "Chọn dòng để tương tác với Inventor"
        StatusPending = New System.Windows.Forms.ToolStripStatusLabel()
        StatusPending.Text = "0 Pending"
        StatusSafeMode = New System.Windows.Forms.ToolStripStatusLabel()
        StatusSafeMode.Text = "EDIT MODE"

        StatusBar.Items.Add(StatusAssembly)
        StatusBar.Items.Add(New System.Windows.Forms.ToolStripStatusLabel("|"))
        StatusBar.Items.Add(StatusParts)
        StatusBar.Items.Add(New System.Windows.Forms.ToolStripStatusLabel("|"))
        StatusBar.Items.Add(StatusVisible)
        StatusBar.Items.Add(New System.Windows.Forms.ToolStripStatusLabel("|"))
        StatusBar.Items.Add(StatusQty)
        StatusBar.Items.Add(New System.Windows.Forms.ToolStripStatusLabel("|"))
        StatusBar.Items.Add(StatusDrawing)
        StatusBar.Items.Add(New System.Windows.Forms.ToolStripStatusLabel("|"))
        StatusBar.Items.Add(StatusLoadTime)
        StatusBar.Items.Add(New System.Windows.Forms.ToolStripStatusLabel("|"))
        StatusBar.Items.Add(StatusSelection)
        StatusBar.Items.Add(New System.Windows.Forms.ToolStripStatusLabel("|"))
        StatusBar.Items.Add(StatusPending)
        StatusBar.Items.Add(New System.Windows.Forms.ToolStripStatusLabel("|"))
        StatusBar.Items.Add(StatusSafeMode)
    End Sub

    Private Sub BuildContextMenu()
        ContextMenu = New ContextMenuStrip()
        AddMenuItem("Mở Part", AddressOf OpenPartClicked)
        AddMenuItem("Mở Drawing", AddressOf OpenDrawingClicked)
        AddMenuItem("Tìm/Chỉ định Drawing...", AddressOf LocateDrawingClicked)
        AddMenuItem("Mở thư mục chứa file", AddressOf OpenFolderClicked)
        ContextMenu.Items.Add(New ToolStripSeparator())
        AddMenuItem("Copy ô hiện tại", AddressOf CopyCurrentCellClicked)
        AddMenuItem("Cut vùng đã chọn", AddressOf CutSelectedCellsClicked)
        AddMenuItem("Copy vùng đã chọn", AddressOf CopySelectedCellsClicked)
        AddMenuItem("Paste vào bảng", AddressOf PasteCellsClicked)
        AddMenuItem("Fill Down", AddressOf FillDownClicked)
        AddMenuItem("Fill Right", AddressOf FillRightClicked)
        AddMenuItem("Xóa nội dung ô", AddressOf ClearSelectedCellsClicked)
        AddMenuItem("Chọn tất cả ô", AddressOf SelectAllCellsClicked)
        AddMenuItem("Chọn toàn bộ cột", AddressOf SelectCurrentColumnClicked)
        AddMenuItem("Chọn toàn bộ hàng", AddressOf SelectCurrentRowClicked)
        AddMenuItem("Chọn cả dòng (Ctrl/Shift)", AddressOf ToggleCellSelectionModeClicked)
        AddMenuItem("Sắp xếp A → Z", AddressOf SortAscendingClicked)
        AddMenuItem("Sắp xếp Z → A", AddressOf SortDescendingClicked)
        AddMenuItem("Sắp xếp theo Stock Number", AddressOf SortByStockNumberClicked)
        AddMenuItem("Auto Fit cột", AddressOf AutoFitSelectedColumnsClicked)
        AddMenuItem("Ẩn cột đã chọn", AddressOf HideSelectedColumnsClicked)
        AddMenuItem("Hiện tất cả cột", AddressOf ShowAllColumnsClicked)
        AddMenuItem("Freeze đến cột hiện tại", AddressOf FreezeToCurrentColumnClicked)
        AddMenuItem("Bỏ Freeze cột", AddressOf UnfreezeColumnsClicked)
        ContextMenu.Items.Add(New ToolStripSeparator())
        AddMenuItem("Highlight trong Assembly", AddressOf HighlightClicked)
        AddMenuItem("Zoom đến Part/Assembly", AddressOf ZoomClicked)
        AddMenuItem("Đồng bộ ngay từ Inventor → BOM", AddressOf SyncFromInventorClicked)
        ContextMenu.Items.Add(New ToolStripSeparator())
        _menuAutoZoom = AddCheckMenuItem("Tự Zoom khi chọn dòng", _autoZoomOnClick, AddressOf AutoZoomOptionChanged)
        _menuHighlightAll = AddCheckMenuItem("Highlight tất cả occurrence cùng Part", _highlightAllOccurrences, AddressOf HighlightAllOptionChanged)
        _menuTwoWaySync = AddCheckMenuItem("Đồng bộ 2 chiều Inventor ↔ BOM", _syncInventorToBom, AddressOf TwoWaySyncOptionChanged)
        ContextMenu.Items.Add(New ToolStripSeparator())
        AddMenuItem("Đánh dấu / Bỏ đánh dấu hàng", AddressOf ToggleMarkClicked)
        AddMenuItem("Thu gọn / Mở rộng nhóm Assembly", AddressOf ToggleCurrentGroupClicked)
        AddMenuItem("Where Used", AddressOf WhereUsedClicked)
        AddMenuItem("Impact Analysis", AddressOf ImpactAnalysisClicked)
        AddMenuItem("Capture Snapshot", AddressOf CaptureSnapshotClicked)
        AddMenuItem("Compare Snapshot", AddressOf CompareSnapshotClicked)
        AddMenuItem("Export Change Report", AddressOf ChangeReportClicked)
        AddMenuItem("Manufacturing Summary", AddressOf ManufacturingSummaryClicked)
        AddMenuItem("Export Manufacturing CSV", AddressOf ManufacturingExportClicked)
        AddMenuItem("Report Center", AddressOf ReportCenterClicked)
        AddMenuItem("Export BOM Report CSV", AddressOf ReportCsvClicked)
        AddMenuItem("Export BOM Report HTML", AddressOf ReportHtmlClicked)
        AddMenuItem("Command Palette", AddressOf CommandPaletteClicked)
        AddMenuItem("Quick Filter", AddressOf QuickFilterClicked)
        AddMenuItem("Health Check", AddressOf HealthCheckClicked)
        AddMenuItem("Recover UI", AddressOf RecoverUiClicked)
        AddMenuItem("Final Regression Check", AddressOf FinalRegressionClicked)
        ContextMenu.Items.Add(New ToolStripSeparator())
        AddMenuItem("Inventor - Ẩn / Hiện", AddressOf ToggleOccurrenceVisibilityClicked)
        AddMenuItem("Inventor - Suppress", AddressOf SuppressOccurrencesClicked)
        AddMenuItem("Inventor - Unsuppress", AddressOf UnsuppressOccurrencesClicked)
        AddMenuItem("Inventor - Isolate", AddressOf IsolateOccurrencesClicked)
        AddMenuItem("Inventor - Restore Isolate", AddressOf RestoreIsolationClicked)
        AddMenuItem("Inventor - Ground / Unground", AddressOf ToggleGroundedClicked)
        ContextMenu.Items.Add(New ToolStripSeparator())
        AddMenuItem("Chỉnh sửa ô iProperty", AddressOf BeginEditPropertyClicked)
        AddMenuItem("Làm mới dòng", AddressOf RefreshSelectedClicked)
        AddMenuItem("Thông tin Cache", AddressOf CacheInfoClicked)
        AddMenuItem("Xuất dòng đã chọn", AddressOf ExportSelectedClicked)
        ContextMenu.Items.Add(New ToolStripSeparator())
        AddMenuItem("Copy Part Number", AddressOf CopyPartNumberClicked)
        AddMenuItem("Copy đường dẫn", AddressOf CopyPathClicked)
        Grid.ContextMenuStrip = ContextMenu
    End Sub

    Private Sub AddMenuItem(ByVal caption As String, ByVal handler As EventHandler)
        Dim item As New ToolStripMenuItem(caption)
        AddHandler item.Click, handler
        ContextMenu.Items.Add(item)
    End Sub


    Private Function AddCheckMenuItem(ByVal caption As String, ByVal checkedValue As Boolean, ByVal handler As EventHandler) As ToolStripMenuItem
        Dim item As New ToolStripMenuItem(caption)
        item.CheckOnClick = True
        item.Checked = checkedValue
        AddHandler item.CheckedChanged, handler
        ContextMenu.Items.Add(item)
        Return item
    End Function

    Private Sub AutoHighlightOptionChanged(ByVal sender As Object, ByVal e As EventArgs)
        'Giữ method để tương thích code cũ nhưng Auto Highlight đã bị vô hiệu hóa.
        _autoHighlightOnClick = False
        If _menuAutoHighlight IsNot Nothing Then _menuAutoHighlight.Checked = False
    End Sub

    Private Sub AutoZoomOptionChanged(ByVal sender As Object, ByVal e As EventArgs)
        _autoZoomOnClick = (_menuAutoZoom IsNot Nothing AndAlso _menuAutoZoom.Checked)
    End Sub

    Private Sub HighlightAllOptionChanged(ByVal sender As Object, ByVal e As EventArgs)
        _highlightAllOccurrences = (_menuHighlightAll Is Nothing OrElse _menuHighlightAll.Checked)
        'Không Highlight ngay; chỉ áp dụng ở lần nhấn HIGHLIGHT/ZOOM tiếp theo.
    End Sub

    Private Sub TwoWaySyncOptionChanged(ByVal sender As Object, ByVal e As EventArgs)
        _syncInventorToBom = (_menuTwoWaySync Is Nothing OrElse _menuTwoWaySync.Checked)
    End Sub



'####################################################################
' SUBSECTION 15.05 - UNIT DISPLAY / GRID COLUMNS
'####################################################################

    Private Sub UnitManagerClicked(ByVal sender As Object, ByVal e As EventArgs)
        Try
            Using unitForm As New Form()
                unitForm.Text = "BOM TOOL PRO - UNIT MANAGER"
                unitForm.StartPosition = FormStartPosition.CenterParent
                unitForm.FormBorderStyle = FormBorderStyle.FixedDialog
                unitForm.MaximizeBox = False
                unitForm.MinimizeBox = False
                unitForm.ClientSize = New Size(430, 270)
                unitForm.Font = New Font("Segoe UI", 9.0F)

                Dim labels() As String = {"Khối lượng", "Chiều dài / Thickness / Bounding Box", "Diện tích", "Thể tích"}
                Dim options As String()() = { _
                    New String() {"kg", "g", "mg", "lb", "oz", "ton"}, _
                    New String() {"mm", "cm", "m", "inch", "ft"}, _
                    New String() {"mm²", "cm²", "m²", "inch²", "ft²"}, _
                    New String() {"mm³", "cm³", "L", "m³", "inch³", "ft³"} _
                }
                Dim current() As String = {BomUnitManager.MassUnit, BomUnitManager.LengthUnit, BomUnitManager.AreaUnit, BomUnitManager.VolumeUnit}
                Dim combos As New List(Of ComboBox)()

                For i As Integer = 0 To 3
                    Dim lbl As New Label()
                    lbl.Text = labels(i)
                    lbl.Left = 22
                    lbl.Top = 24 + i * 48
                    lbl.Width = 235
                    lbl.Height = 26
                    lbl.TextAlign = ContentAlignment.MiddleLeft
                    unitForm.Controls.Add(lbl)

                    Dim cbo As New ComboBox()
                    cbo.DropDownStyle = ComboBoxStyle.DropDownList
                    cbo.Left = 270
                    cbo.Top = 23 + i * 48
                    cbo.Width = 125
                    cbo.Items.AddRange(options(i))
                    cbo.SelectedItem = current(i)
                    If cbo.SelectedIndex < 0 Then cbo.SelectedIndex = 0
                    unitForm.Controls.Add(cbo)
                    combos.Add(cbo)
                Next

                Dim okButton As New Button()
                okButton.Text = "ÁP DỤNG"
                okButton.DialogResult = DialogResult.OK
                okButton.Left = 220
                okButton.Top = 218
                okButton.Width = 95
                unitForm.Controls.Add(okButton)

                Dim cancelButton As New Button()
                cancelButton.Text = "HỦY"
                cancelButton.DialogResult = DialogResult.Cancel
                cancelButton.Left = 322
                cancelButton.Top = 218
                cancelButton.Width = 72
                unitForm.Controls.Add(cancelButton)
                unitForm.AcceptButton = okButton
                unitForm.CancelButton = cancelButton

                If unitForm.ShowDialog(Me) = DialogResult.OK Then
                    BomUnitManager.MassUnit = Convert.ToString(combos(0).SelectedItem)
                    BomUnitManager.LengthUnit = Convert.ToString(combos(1).SelectedItem)
                    BomUnitManager.AreaUnit = Convert.ToString(combos(2).SelectedItem)
                    BomUnitManager.VolumeUnit = Convert.ToString(combos(3).SelectedItem)
                    RefreshUnitDisplay()
                End If
            End Using
        Catch ex As Exception
            MessageBox.Show("Không thể đổi đơn vị:" & vbCrLf & ex.Message, "BOM TOOL PRO", MessageBoxButtons.OK, MessageBoxIcon.Warning)
        End Try
    End Sub

    Private Sub RefreshUnitDisplay()
        Grid.SuspendLayout()
        Try
            If Grid.Columns.Contains("THICKNESS") Then Grid.Columns("THICKNESS").HeaderText = "THICK (" & BomUnitManager.LengthUnit & ")"
            If Grid.Columns.Contains("BOUNDING_BOX") Then Grid.Columns("BOUNDING_BOX").HeaderText = "BOUNDING BOX L x W x H (" & BomUnitManager.LengthUnit & ")"
            For Each p As PropertyColumnInfo In _selectedProperties
                If Grid.Columns.Contains(p.Key) Then Grid.Columns(p.Key).HeaderText = BomUnitManager.GetPropertyHeader(p.PropertyName)
            Next

            For Each row As DataGridViewRow In Grid.Rows
                Dim item As PartBomItem = TryCast(row.Tag, PartBomItem)
                If item Is Nothing Then Continue For
                If Grid.Columns.Contains("THICKNESS") Then row.Cells("THICKNESS").Value = BomUnitManager.FormatLength(item.Thickness)
                If Grid.Columns.Contains("BOUNDING_BOX") Then row.Cells("BOUNDING_BOX").Value = BomUnitManager.FormatBoundingBox(item)
                For Each p As PropertyColumnInfo In _selectedProperties
                    If Grid.Columns.Contains(p.Key) Then row.Cells(p.Key).Value = BomUnitManager.GetPropertyDisplayValue(item, p)
                Next
            Next
            StatusLoadTime.Text = "Đơn vị: " & BomUnitManager.MassUnit & " | " & BomUnitManager.LengthUnit & " | " & BomUnitManager.AreaUnit & " | " & BomUnitManager.VolumeUnit
        Finally
            Grid.ResumeLayout()
        End Try
    End Sub

    Private Sub BuildColumns()
        Grid.Columns.Clear()
        _excelHeaderTitles.Clear()
        AddColumn("ITEM", "ITEM", 62, True, False)
        AddColumn("QTY", "QTY", 62, True, False)
        If _includeFileName Then AddColumn("FILE_NAME", "FILE NAME", 150, False, False)
        If _includeFilePath Then AddColumn("FILE_PATH", "FILE PATH", 330, False, False)
        If _includeParentAssembly Then AddColumn("PARENT_ASSEMBLY", "NẰM TRONG ASSEMBLY", 190, False, False)
        AddColumn("DRAWING_STATUS", "DRAWING", 92, True, False)
        AddColumn("DATA_STATUS", "DATA STATUS", 170, False, False)

        'Không tự động hiện Feature chưa chọn.
        For Each featureKey As String In _enabledFeatures
            AddFeatureColumn(featureKey)
        Next

        For Each p As PropertyColumnInfo In _selectedProperties
            AddPropertyColumn(p)
        Next
    End Sub

    Private Sub AddPropertyColumn(ByVal p As PropertyColumnInfo)
        If Grid.Columns.Contains(p.Key) Then Exit Sub
        Dim isEditable As Boolean = IsEditableProperty(p.PropertyName)
        AddColumn(p.Key, BomUnitManager.GetPropertyHeader(p.PropertyName), CInt(GetRecommendedColumnWidth(p.PropertyName) * 7), False, isEditable)
        Dim col As DataGridViewColumn = Grid.Columns(p.Key)
        col.Tag = p
        col.ToolTipText = If(isEditable, "Có thể chỉnh sửa trực tiếp. Nhấn F2 hoặc nhập dữ liệu.", "Thuộc tính chỉ đọc hoặc không nên sửa trực tiếp.")
    End Sub

    Private Sub AddColumn(ByVal name As String, ByVal header As String, ByVal width As Integer, ByVal centered As Boolean, ByVal editable As Boolean)
        Dim col As New System.Windows.Forms.DataGridViewTextBoxColumn()
        col.Name = name
        _excelHeaderTitles(name) = header
        col.HeaderText = ColumnIndexToExcelName(Grid.Columns.Count) & vbCrLf & header
        col.Width = Math.Max(55, width)
        col.MinimumWidth = 48
        col.ReadOnly = Not editable
        'V13.2: bắt buộc Programmatic. Automatic sẽ trộn Assembly Header với Part rows.
        col.SortMode = System.Windows.Forms.DataGridViewColumnSortMode.Programmatic
        col.AutoSizeMode = System.Windows.Forms.DataGridViewAutoSizeColumnMode.None
        If centered Then col.DefaultCellStyle.Alignment = System.Windows.Forms.DataGridViewContentAlignment.MiddleCenter
        Grid.Columns.Add(col)
    End Sub

    Private Sub AddImageColumn(ByVal name As String, ByVal header As String, ByVal width As Integer)
        If Grid.Columns.Contains(name) Then Exit Sub
        Dim col As New System.Windows.Forms.DataGridViewImageColumn()
        col.Name = name
        _excelHeaderTitles(name) = header
        col.HeaderText = ColumnIndexToExcelName(Grid.Columns.Count) & vbCrLf & header
        col.Width = Math.Max(72, width)
        col.MinimumWidth = 64
        col.ReadOnly = True
        col.SortMode = System.Windows.Forms.DataGridViewColumnSortMode.NotSortable
        col.ImageLayout = System.Windows.Forms.DataGridViewImageCellLayout.Zoom
        Grid.Columns.Add(col)
        col.DisplayIndex = Math.Min(1, Grid.Columns.Count - 1)
    End Sub

    Private Sub AddFeatureColumn(ByVal featureKey As String)
        If String.IsNullOrWhiteSpace(featureKey) OrElse Not _featureRegistry.ContainsKey(featureKey) Then Exit Sub
        Dim f As BomFeatureDefinition = _featureRegistry(featureKey)
        If f.IsImage Then
            AddImageColumn(f.ColumnName, f.HeaderText, f.Width)
        Else
            AddColumn(f.ColumnName, f.HeaderText, f.Width, f.Centered, False)
        End If
    End Sub

    Private Function IsEditableProperty(ByVal propertyName As String) As Boolean
        Dim n As String = If(propertyName, "").Trim().ToUpperInvariant()
        If n = "MASS" OrElse n = "VOLUME" OrElse n = "AREA" OrElse n = "DENSITY" OrElse n = "THUMBNAIL" Then Return False
        If n.Contains("DATE CREATED") OrElse n.Contains("LAST UPDATED") Then Return False
        Return True
    End Function


'####################################################################
' SUBSECTION 15.06 - GRID ROW RENDERING / DATA STATUS
'####################################################################

    Private Sub LoadRows()
        Dim gridWatch As Stopwatch = Stopwatch.StartNew()
        BomPerformanceCounters.GridRefresh += 1
        _suppressCellWrite = True
        Grid.SuspendLayout()
        Grid.Rows.Clear()

        Dim itemNumber As Integer = 0

        If _bomDisplayMode = BomDisplayMode.PartsOnly Then
            _groupedView = False
            Dim flatItems As New List(Of PartBomItem)()
            For Each candidate As PartBomItem In _allItems
                If BomStructurePolicy.IncludeInPartsOnly(candidate) Then flatItems.Add(candidate)
            Next
            SortItemsForCurrentView(flatItems, "")
            For Each item As PartBomItem In flatItems
                itemNumber += 1
                AddPartRow(item, itemNumber, item.Quantity, "")
            Next
        Else
            _groupedView = True
            _structureRoot = BomStructureEngine.Build(_assemblyName, _allItems)
            Dim structureAudit As BomStructureAuditResult = BomStructureAuditEngine.Audit(_structureRoot)
            If structureAudit.Errors.Count > 0 Then
                BomLogger.Log("STRUCTURE", _assemblyName, "Audit", "ERROR",
                              String.Join(" | ", structureAudit.Errors.ToArray()))
            End If
            If structureAudit.Warnings.Count > 0 Then
                BomLogger.Log("STRUCTURE", _assemblyName, "Audit", "WARNING",
                              String.Join(" | ", structureAudit.Warnings.ToArray()))
            End If

            If _bomDisplayMode = BomDisplayMode.Structured Then
                'STRUCTURED: cây Assembly cha-con thật. Part chỉ nằm dưới đúng node trực tiếp.
                AddStructuredNodeRows(_structureRoot, itemNumber, False, True)
            Else
                'HYBRID: cây cha-con + Local Qty ở Part + Total Qty/Unique Part trên Assembly header.
                AddStructuredNodeRows(_structureRoot, itemNumber, True, True)
            End If
        End If

        UpdateSortGlyph()
        Grid.ResumeLayout()
        _suppressCellWrite = False
        ApplySearchFilter()
        gridWatch.Stop()
        BomPerformanceCounters.GridBuildMs += gridWatch.ElapsedMilliseconds
    End Sub

    Private Sub AddStructuredNodeRows(ByVal node As BomAssemblyNode, ByRef itemNumber As Integer, ByVal hybridMode As Boolean, ByVal includeRoot As Boolean)
        If node Is Nothing Then Exit Sub

        If includeRoot Then AddStructuredAssemblyHeaderRow(node, hybridMode)

        Dim entries As List(Of BomAssemblyPartEntry) = node.GetDirectEntries()
        If entries.Count > 0 Then
            Dim items As New List(Of PartBomItem)()
            Dim qtyByKey As New Dictionary(Of String, Integer)(StringComparer.OrdinalIgnoreCase)
            For Each entry As BomAssemblyPartEntry In entries
                If entry Is Nothing OrElse entry.Item Is Nothing Then Continue For
                items.Add(entry.Item)
                Dim key As String = If(String.IsNullOrWhiteSpace(entry.Item.DocumentKey), entry.Item.FilePath, entry.Item.DocumentKey)
                qtyByKey(key) = entry.LocalQuantity
            Next
            SortItemsForCurrentView(items, node.Name)
            For Each item As PartBomItem In items
                itemNumber += 1
                Dim key As String = If(String.IsNullOrWhiteSpace(item.DocumentKey), item.FilePath, item.DocumentKey)
                Dim qInfo As BomQuantityInfo = BomQuantityEngine.ForItemInNode(item, node)
                Dim localQty As Integer = If(qtyByKey.ContainsKey(key), qtyByKey(key), qInfo.LocalQty)
                If localQty <= 0 Then localQty = qInfo.LocalQty
                AddPartRow(item, itemNumber, localQty, node.Name)
                Dim row As DataGridViewRow = Grid.Rows(Grid.Rows.Count - 1)
                row.HeaderCell.Tag = node.FullPath
                row.Cells("ITEM").Style.Padding = New Padding(Math.Min(48, (node.Level + 1) * 12), 0, 0, 0)
                If Grid.Columns.Contains("DATA_STATUS") Then
                    Dim qInfo2 As BomQuantityInfo = BomQuantityEngine.ForItemInNode(item, node)
                    Dim structureText As String = BomStructurePolicy.StatusText(item)
                    row.Cells("DATA_STATUS").ToolTipText = "BOM: " & structureText &
                        " | LOCAL QTY: " & localQty.ToString() &
                        " | PARENT QTY: " & qInfo2.ParentQty.ToString() &
                        " | EFFECTIVE QTY: " & qInfo2.EffectiveQty.ToString() &
                        " | TOTAL QTY: " & qInfo2.TotalQty.ToString() &
                        " | VISIBLE: " & qInfo2.VisibleQty.ToString() &
                        " | SUPPRESSED: " & qInfo2.SuppressedQty.ToString()
                    If BomStructurePolicy.IsReference(item) Then
                        row.DefaultCellStyle.Font = New Font(row.DefaultCellStyle.Font, FontStyle.Italic)
                        row.Cells("DATA_STATUS").Value = "REFERENCE"
                    ElseIf BomStructurePolicy.IsPurchased(item) Then
                        row.Cells("DATA_STATUS").Value = "PURCHASED"
                    ElseIf BomStructurePolicy.IsInseparable(item) Then
                        row.Cells("DATA_STATUS").Value = "INSEPARABLE"
                    ElseIf BomStructurePolicy.IsPhantom(item) Then
                        row.Cells("DATA_STATUS").Value = "PHANTOM"
                    End If
                End If
            Next
        End If

        For Each child As BomAssemblyNode In node.GetSortedChildren()
            AddStructuredNodeRows(child, itemNumber, hybridMode, True)
        Next
    End Sub

    Private Sub AddStructuredAssemblyHeaderRow(ByVal node As BomAssemblyNode, ByVal hybridMode As Boolean)
        If node Is Nothing Then Exit Sub
        Dim rowIndex As Integer = Grid.Rows.Add()
        Dim row As DataGridViewRow = Grid.Rows(rowIndex)
        row.Tag = Nothing
        row.HeaderCell.Tag = node.FullPath
        row.Height = 31
        row.ReadOnly = True
        row.DefaultCellStyle.BackColor = Color.FromArgb(45, 165, 180)
        row.DefaultCellStyle.ForeColor = Color.White
        row.DefaultCellStyle.SelectionBackColor = Color.FromArgb(34, 140, 154)
        row.DefaultCellStyle.SelectionForeColor = Color.White
        row.DefaultCellStyle.Font = New Font("Segoe UI Semibold", 9.5F, FontStyle.Bold)

        Dim collapsed As Boolean = _collapsedGroups.Contains(node.FullPath)
        row.Cells("ITEM").Value = If(collapsed, "▸", "▾")
        row.Cells("ITEM").Style.Padding = New Padding(Math.Min(48, node.Level * 12), 0, 0, 0)

        Dim recursiveQty As Integer = node.GetRecursiveQuantity()
        row.Cells("QTY").Value = recursiveQty.ToString()
        Dim titleColumn As String = If(Grid.Columns.Contains("FILE_NAME"), "FILE_NAME", If(Grid.Columns.Contains("PARENT_ASSEMBLY"), "PARENT_ASSEMBLY", "DATA_STATUS"))
        Dim title As String = "📁  " & node.Name
        If hybridMode Then
            title &= "   | UNIQUE " & node.GetRecursiveUniquePartCount().ToString() & " | TOTAL QTY " & recursiveQty.ToString()
        Else
            title &= "   (" & node.DirectParts.Count.ToString() & " direct Part)"
        End If
        row.Cells(titleColumn).Value = title
        row.Cells("DATA_STATUS").Value = If(hybridMode, "HYBRID", "STRUCTURED")
        Dim normalCount As Integer = 0, purchasedCount As Integer = 0, phantomCount As Integer = 0, referenceCount As Integer = 0, inseparableCount As Integer = 0
        CountStructureTypes(node, normalCount, purchasedCount, phantomCount, referenceCount, inseparableCount)
        row.Cells("DATA_STATUS").ToolTipText = "PATH: " & node.FullPath &
            " | NORMAL " & normalCount.ToString() &
            " | PURCHASED " & purchasedCount.ToString() &
            " | PHANTOM " & phantomCount.ToString() &
            " | REFERENCE " & referenceCount.ToString() &
            " | INSEPARABLE " & inseparableCount.ToString() &
            " | PHANTOM POLICY: roll-up/flatten in effective BOM; REFERENCE excluded from effective quantity." 
    End Sub

    Private Sub CountStructureTypes(ByVal node As BomAssemblyNode,
                                        ByRef normalCount As Integer,
                                        ByRef purchasedCount As Integer,
                                        ByRef phantomCount As Integer,
                                        ByRef referenceCount As Integer,
                                        ByRef inseparableCount As Integer)
        If node Is Nothing Then Exit Sub
        For Each entry As BomAssemblyPartEntry In node.DirectParts.Values
            If entry Is Nothing OrElse entry.Item Is Nothing Then Continue For
            Select Case BomStructurePolicy.Normalize(entry.Item.BomStructure)
                Case "PURCHASED" : purchasedCount += 1
                Case "PHANTOM" : phantomCount += 1
                Case "REFERENCE" : referenceCount += 1
                Case "INSEPARABLE" : inseparableCount += 1
                Case Else : normalCount += 1
            End Select
        Next
        For Each child As BomAssemblyNode In node.Children.Values
            CountStructureTypes(child, normalCount, purchasedCount, phantomCount, referenceCount, inseparableCount)
        Next
    End Sub

    Private Sub AddAssemblyHeaderRow(ByVal assemblyName As String, ByVal items As List(Of PartBomItem))
        Dim totalQty As Integer = 0
        For Each item As PartBomItem In items
            totalQty += Math.Max(1, item.GetQuantityForParent(assemblyName))
        Next
        Dim rowIndex As Integer = Grid.Rows.Add()
        Dim row As DataGridViewRow = Grid.Rows(rowIndex)
        row.Tag = Nothing
        row.HeaderCell.Tag = assemblyName
        row.Height = 31
        row.ReadOnly = True
        Dim cyanHeader As Color = Color.FromArgb(45, 165, 180)
        Dim cyanSelected As Color = Color.FromArgb(34, 140, 154)
        row.DefaultCellStyle.BackColor = cyanHeader
        row.DefaultCellStyle.ForeColor = Color.White
        row.DefaultCellStyle.SelectionBackColor = cyanSelected
        row.DefaultCellStyle.SelectionForeColor = Color.White
        row.DefaultCellStyle.Font = New Font("Segoe UI Semibold", 9.5F, FontStyle.Bold)
        row.Cells("ITEM").Value = If(_collapsedGroups.Contains(assemblyName), "▸", "▾")
        row.Cells("QTY").Value = totalQty.ToString()
        Dim titleColumn As String = If(Grid.Columns.Contains("FILE_NAME"), "FILE_NAME", If(Grid.Columns.Contains("PARENT_ASSEMBLY"), "PARENT_ASSEMBLY", "DATA_STATUS"))
        row.Cells(titleColumn).Value = "📁  " & assemblyName & "   (" & items.Count.ToString() & " loại Part)"
        row.Cells("DATA_STATUS").Value = "ASSEMBLY GROUP"
    End Sub

    Private Sub AddPartRow(ByVal item As PartBomItem, ByVal itemNumber As Integer, ByVal groupQty As Integer, ByVal groupName As String)
        Dim drawingStatus As String = GetDrawingStatus(item.FilePath)
        Dim dataStatus As String = GetDataStatus(item)
        item.DataStatus = dataStatus
        Dim values As New Dictionary(Of String, Object)(StringComparer.OrdinalIgnoreCase)
        values("ITEM") = itemNumber.ToString()
        values("QTY") = If(groupQty > 0, groupQty, item.Quantity).ToString()
        If _includeFileName Then values("FILE_NAME") = item.FileName
        If _includeFilePath Then values("FILE_PATH") = item.FilePath
        If _includeParentAssembly Then values("PARENT_ASSEMBLY") = If(groupName.Length > 0, groupName, item.GetParentAssemblyText())
        values("DRAWING_STATUS") = drawingStatus
        For Each featureKey As String In _enabledFeatures
            If _featureRegistry.ContainsKey(featureKey) Then
                Dim f As BomFeatureDefinition = _featureRegistry(featureKey)
                values(f.ColumnName) = GetFeatureDisplayValue(item, featureKey)
            End If
        Next
        values("DATA_STATUS") = dataStatus
        For Each p As PropertyColumnInfo In _selectedProperties
            Dim value As Object = BomUnitManager.GetPropertyDisplayValue(item, p)
            values(p.Key) = If(value Is Nothing, "", value)
        Next

        Dim rowIndex As Integer = Grid.Rows.Add()
        Dim row As DataGridViewRow = Grid.Rows(rowIndex)
        row.Tag = item
        row.HeaderCell.Tag = groupName
        For Each pair As KeyValuePair(Of String, Object) In values
            If Grid.Columns.Contains(pair.Key) Then row.Cells(pair.Key).Value = pair.Value
        Next
        row.DefaultCellStyle.BackColor = If(_markedPartKeys.Contains(item.DocumentKey), Color.FromArgb(255, 245, 170), Color.White)
        If _groupedView AndAlso groupName.Length > 0 AndAlso IsPathCollapsed(groupName) Then row.Visible = False
        If drawingStatus = "MISSING" Then
            row.Cells("DRAWING_STATUS").Style.BackColor = Color.White
            row.Cells("DRAWING_STATUS").Style.ForeColor = Color.FromArgb(205, 45, 45)
        End If
        If dataStatus <> "OK" Then
            row.Cells("DATA_STATUS").Style.BackColor = Color.White
            row.Cells("DATA_STATUS").Style.ForeColor = Color.FromArgb(185, 95, 20)
        End If
    End Sub

    Private Function GetDrawingStatus(ByVal partPath As String) As String
        If _scanMode = BomScanMode.Fast Then Return "SKIPPED"
        If String.IsNullOrWhiteSpace(partPath) Then Return "MISSING"
        Dim drawingPath As String = FindDrawingPath(partPath)
        If String.IsNullOrWhiteSpace(drawingPath) Then Return "MISSING"
        Return IOPath.GetExtension(drawingPath).TrimStart("."c).ToUpperInvariant()
    End Function

    Private Function GetDataStatus(ByVal item As PartBomItem) As String
        Dim missing As New List(Of String)()
        For Each p As PropertyColumnInfo In _selectedProperties
            Dim n As String = p.PropertyName.Trim().ToUpperInvariant()
            If n = "PART NUMBER" OrElse n = "DESCRIPTION" OrElse n = "MATERIAL" Then
                Dim value As String = ""
                If item.SelectedPropertyValues.ContainsKey(p.Key) Then value = Convert.ToString(item.SelectedPropertyValues(p.Key)).Trim()
                If value.Length = 0 Then missing.Add(p.PropertyName)
            End If
        Next
        If item IsNot Nothing AndAlso String.Equals(item.GeometryLoadState, "LOADED", StringComparison.OrdinalIgnoreCase) Then
            If item.IsSheetMetal AndAlso item.Thickness <= 0 Then missing.Add("THICK")
            If (item.GeometryType = "PLATE / LEG" OrElse item.GeometryType = "THIN PART") AndAlso item.Thickness <= 0 Then missing.Add("THICK")
            If item.GeometryType = "GENERAL PART" AndAlso String.IsNullOrWhiteSpace(item.BoundingBoxText) Then missing.Add("BOUNDING BOX")
        End If
        If missing.Count = 0 Then Return "OK"
        Return "MISSING: " & String.Join(", ", missing.ToArray())
    End Function


'####################################################################
' SUBSECTION 15.07 - ASSEMBLY FILTER / SEARCH ENGINE
'####################################################################

    Private Sub BuildAssemblyFilterItems()
        If AssemblyFilterBox Is Nothing Then Exit Sub
        Dim currentText As String = AssemblyFilterBox.Text
        Dim names As New SortedSet(Of String)(StringComparer.OrdinalIgnoreCase)
        names.Add(_assemblyName)
        For Each parentName As String In _runtimeIndex.ItemsByAssembly.Keys
            If Not String.IsNullOrWhiteSpace(parentName) Then names.Add(parentName)
        Next
        AssemblyFilterBox.BeginUpdate()
        AssemblyFilterBox.Items.Clear()
        AssemblyFilterBox.Items.Add("<TẤT CẢ ASSEMBLY>")
        For Each name As String In names
            AssemblyFilterBox.Items.Add(name)
        Next
        AssemblyFilterBox.EndUpdate()
        If currentText.Length > 0 AndAlso AssemblyFilterBox.Items.Contains(currentText) Then
            AssemblyFilterBox.SelectedItem = currentText
        Else
            AssemblyFilterBox.SelectedIndex = 0
        End If
    End Sub

    Private Sub AssemblyFilterChanged(ByVal sender As Object, ByVal e As EventArgs)
        If _searchTimer Is Nothing Then Exit Sub
        _searchTimer.Stop()
        _searchTimer.Start()
    End Sub

    Private Function GetSelectedAssemblyFilter() As String
        If AssemblyFilterBox Is Nothing Then Return ""
        Dim value As String = AssemblyFilterBox.Text.Trim()
        If value.Length = 0 OrElse value = "<TẤT CẢ ASSEMBLY>" Then Return ""
        Return value
    End Function

    Private Function ItemBelongsToAssembly(ByVal item As PartBomItem, ByVal assemblyName As String) As Boolean
        Return _runtimeIndex.BelongsToAssembly(item, assemblyName, _assemblyName)
    End Function

    Private Sub UpdateAssemblyFilterInfo(ByVal assemblyName As String, ByVal uniqueCount As Integer, ByVal totalQty As Integer)
        If AssemblyFilterInfo Is Nothing Then Exit Sub
        If String.IsNullOrWhiteSpace(assemblyName) Then
            AssemblyFilterInfo.Text = "Tất cả Assembly | " & uniqueCount.ToString() & " loại Part | QTY " & totalQty.ToString()
        Else
            AssemblyFilterInfo.Text = assemblyName & " | " & uniqueCount.ToString() & " loại Part | QTY " & totalQty.ToString()
        End If
    End Sub

    Private Sub SearchChanged(ByVal sender As Object, ByVal e As EventArgs)
        If _searchTimer Is Nothing Then
            ApplySearchFilter()
            Exit Sub
        End If
        _searchTimer.Stop()
        _searchTimer.Start()
    End Sub

    Private Sub SearchTimerTick(ByVal sender As Object, ByVal e As EventArgs)
        _searchTimer.Stop()
        ApplySearchFilter()
    End Sub

    Private Sub ApplySearchFilter()
        Dim term As String = SearchBox.Text.Trim()
        Dim selectedAssembly As String = GetSelectedAssemblyFilter()
        Dim visibleCount As Integer = 0
        Dim totalQty As Integer = 0
        Dim missingDrawing As Integer = 0
        Dim currentHeader As DataGridViewRow = Nothing
        Dim currentGroupName As String = ""
        Dim headerHasVisibleChild As Boolean = False

        For Each row As DataGridViewRow In Grid.Rows
            If IsAssemblyHeaderRow(row) Then
                If currentHeader IsNot Nothing Then currentHeader.Visible = headerHasVisibleChild OrElse (term.Length = 0 AndAlso selectedAssembly.Length = 0)
                currentHeader = row
                currentGroupName = GetRowGroupName(row)
                headerHasVisibleChild = False
                row.Visible = _groupedView
            Else
                Dim cachedItem As PartBomItem = TryCast(row.Tag, PartBomItem)
                Dim rowGroup As String = GetRowGroupName(row)
                Dim assemblyMatch As Boolean = ItemBelongsToAssembly(cachedItem, selectedAssembly)
                If _groupedView AndAlso selectedAssembly.Length > 0 AndAlso Not String.Equals(selectedAssembly, _assemblyName, StringComparison.OrdinalIgnoreCase) Then
                    assemblyMatch = assemblyMatch AndAlso String.Equals(rowGroup, selectedAssembly, StringComparison.OrdinalIgnoreCase)
                End If
                Dim visible As Boolean = assemblyMatch AndAlso term.Length = 0
                If assemblyMatch AndAlso Not visible AndAlso cachedItem IsNot Nothing Then
                    visible = CachedSearchMatch(cachedItem, term)
                End If
                If assemblyMatch AndAlso Not visible Then
                    For Each cell As System.Windows.Forms.DataGridViewCell In row.Cells
                        If cell.Value IsNot Nothing AndAlso Convert.ToString(cell.Value).IndexOf(term, StringComparison.OrdinalIgnoreCase) >= 0 Then
                            visible = True
                            Exit For
                        End If
                    Next
                End If

                If _groupedView AndAlso rowGroup.Length > 0 AndAlso _collapsedGroups.Contains(rowGroup) Then visible = False

                row.Visible = visible
                If visible Then
                    headerHasVisibleChild = True
                    visibleCount += 1
                    Dim item As PartBomItem = TryCast(row.Tag, PartBomItem)
                    If item IsNot Nothing Then
                        If selectedAssembly.Length > 0 AndAlso Not String.Equals(selectedAssembly, _assemblyName, StringComparison.OrdinalIgnoreCase) Then
                            totalQty += Math.Max(0, item.GetQuantityForParent(selectedAssembly))
                        Else
                            Dim shownQty As Integer = 0
                            Integer.TryParse(Convert.ToString(row.Cells("QTY").Value), shownQty)
                            totalQty += Math.Max(0, shownQty)
                        End If
                    End If
                    If Convert.ToString(row.Cells("DRAWING_STATUS").Value) = "MISSING" Then missingDrawing += 1
                End If
            End If
        Next
        If currentHeader IsNot Nothing Then currentHeader.Visible = headerHasVisibleChild OrElse (term.Length = 0 AndAlso selectedAssembly.Length = 0)
        UpdateAssemblyFilterInfo(selectedAssembly, visibleCount, totalQty)
        UpdateStatusBar(visibleCount, totalQty, missingDrawing)
    End Sub

    Private Function CachedSearchMatch(ByVal item As PartBomItem, ByVal expression As String) As Boolean
        If item Is Nothing OrElse String.IsNullOrWhiteSpace(expression) Then Return True
        Dim blob As String = If(item.SearchBlob, "")
        Dim query As String = expression.Trim()
        Try
            If query.StartsWith("regex:", StringComparison.OrdinalIgnoreCase) Then
                Return Regex.IsMatch(blob, query.Substring(6), RegexOptions.IgnoreCase)
            End If
        Catch
            Return False
        End Try
        Dim orGroups() As String = query.Split(New String() {" OR ", "|"}, StringSplitOptions.RemoveEmptyEntries)
        For Each groupText As String In orGroups
            Dim groupMatched As Boolean = True
            Dim tokens() As String = groupText.Trim().Split(New Char() {" "c, "+"c}, StringSplitOptions.RemoveEmptyEntries)
            For Each tokenRaw As String In tokens
                Dim token As String = tokenRaw.Trim()
                Dim isNegativeToken As Boolean = token.StartsWith("-") OrElse token.StartsWith("!")
                If isNegativeToken Then token = token.Substring(1)
                token = token.Replace("*", "")
                If token.Length = 0 Then Continue For
                Dim containsToken As Boolean = blob.IndexOf(token, StringComparison.OrdinalIgnoreCase) >= 0
                If (Not isNegativeToken AndAlso Not containsToken) OrElse (isNegativeToken AndAlso containsToken) Then
                    groupMatched = False
                    Exit For
                End If
            Next
            If groupMatched Then Return True
        Next
        Return False
    End Function

    Private Function IsAssemblyHeaderRow(ByVal row As DataGridViewRow) As Boolean
        Return row IsNot Nothing AndAlso row.Tag Is Nothing AndAlso Convert.ToString(row.HeaderCell.Tag).Length > 0
    End Function

    Private Function GetRowGroupName(ByVal row As DataGridViewRow) As String
        If row Is Nothing Then Return ""
        Return Convert.ToString(row.HeaderCell.Tag)
    End Function


'####################################################################
' SUBSECTION 15.08 - STATUS / CURRENT ITEM / SELECTION COLLECTION
'####################################################################

    Private Sub UpdateStatusBar(ByVal visibleCount As Integer, ByVal totalQty As Integer, ByVal missingDrawing As Integer)
        StatusAssembly.Text = "Assembly: " & _assemblyName
        StatusParts.Text = "Loại Part: " & _allItems.Count.ToString()
        StatusVisible.Text = "Đang hiện: " & visibleCount.ToString()
        StatusQty.Text = "Tổng QTY: " & totalQty.ToString()
        StatusDrawing.Text = "Thiếu Drawing: " & missingDrawing.ToString()
        StatusLoadTime.Text = "Load: " & _loadedAt.ToString("HH:mm:ss")
    End Sub

    Private Function GetCurrentItem() As PartBomItem
        If Grid.CurrentRow Is Nothing Then Return Nothing
        Return TryCast(Grid.CurrentRow.Tag, PartBomItem)
    End Function

    Private Function GetSelectedItems() As List(Of PartBomItem)
        Dim result As New List(Of PartBomItem)()
        Dim seen As New HashSet(Of String)(StringComparer.OrdinalIgnoreCase)
        For Each row As DataGridViewRow In Grid.SelectedRows
            Dim item As PartBomItem = TryCast(row.Tag, PartBomItem)
            If item IsNot Nothing AndAlso Not seen.Contains(item.DocumentKey) Then
                seen.Add(item.DocumentKey)
                result.Add(item)
            End If
        Next
        For Each cell As System.Windows.Forms.DataGridViewCell In Grid.SelectedCells
            Dim item As PartBomItem = TryCast(cell.OwningRow.Tag, PartBomItem)
            If item IsNot Nothing AndAlso Not seen.Contains(item.DocumentKey) Then
                seen.Add(item.DocumentKey)
                result.Add(item)
            End If
        Next
        If result.Count = 0 Then
            Dim current As PartBomItem = GetCurrentItem()
            If current IsNot Nothing Then result.Add(current)
        End If
        Return result
    End Function

    Private Function GetFilteredItems() As List(Of PartBomItem)
        Dim result As New List(Of PartBomItem)()
        Dim seen As New HashSet(Of String)(StringComparer.OrdinalIgnoreCase)
        For Each row As DataGridViewRow In Grid.Rows
            If row.Visible Then
                Dim item As PartBomItem = TryCast(row.Tag, PartBomItem)
                If item IsNot Nothing AndAlso Not seen.Contains(item.DocumentKey) Then
                    seen.Add(item.DocumentKey)
                    result.Add(item)
                End If
            End If
        Next
        Return result
    End Function


'####################################################################
' SUBSECTION 15.09 - GRID MOUSE / DOUBLE CLICK / SELECTION EVENTS
'####################################################################

    Private Sub GridCellMouseDown(ByVal sender As Object, ByVal e As DataGridViewCellMouseEventArgs)
        _contextColumnIndex = e.ColumnIndex
        _contextRowIndex = e.RowIndex

        'HYBRID SELECTION MODE:
        ' - Click row header => true FullRowSelect so legacy SelectedRows features keep working.
        ' - Click data cell => Excel CellSelect, unless user explicitly locked row mode from menu.
        If e.Button = MouseButtons.Left Then
            If e.ColumnIndex = -1 AndAlso e.RowIndex >= 0 Then
                If Grid.SelectionMode <> DataGridViewSelectionMode.FullRowSelect Then
                    Grid.SelectionMode = DataGridViewSelectionMode.FullRowSelect
                    Grid.MultiSelect = True
                End If
            ElseIf e.ColumnIndex >= 0 AndAlso e.RowIndex >= 0 AndAlso Not _forceFullRowSelection Then
                If Grid.SelectionMode <> DataGridViewSelectionMode.CellSelect Then
                    Grid.SelectionMode = DataGridViewSelectionMode.CellSelect
                    Grid.MultiSelect = True
                End If
            End If
        End If

        'Bắt fill handle trước các xử lý chọn ô/dòng thông thường.
        If e.Button = MouseButtons.Left AndAlso e.RowIndex >= 0 AndAlso e.ColumnIndex >= 0 AndAlso Grid.CurrentCell IsNot Nothing Then
            If Grid.CurrentCell.RowIndex = e.RowIndex AndAlso Grid.CurrentCell.ColumnIndex = e.ColumnIndex Then
                Dim col As DataGridViewColumn = Grid.Columns(e.ColumnIndex)
                Dim item As PartBomItem = TryCast(Grid.Rows(e.RowIndex).Tag, PartBomItem)
                Dim pi As PropertyColumnInfo = TryCast(col.Tag, PropertyColumnInfo)
                Dim cellRect As Rectangle = Grid.GetCellDisplayRectangle(e.ColumnIndex, e.RowIndex, False)
                Dim mousePoint As Point = Grid.PointToClient(Control.MousePosition)
                Dim handleRect As New Rectangle(cellRect.Right - FillHandleSize - 1, cellRect.Bottom - FillHandleSize - 1, FillHandleSize + 2, FillHandleSize + 2)
                If item IsNot Nothing AndAlso pi IsNot Nothing AndAlso Not col.ReadOnly AndAlso handleRect.Contains(mousePoint) Then
                    _fillDragging = True
                    _fillSourceRow = e.RowIndex
                    _fillSourceColumn = e.ColumnIndex
                    _fillTargetRow = e.RowIndex
                    Grid.Capture = True
                    Exit Sub
                End If
            End If
        End If

        'Ô góc trái trên cùng: chọn toàn bộ bảng giống Excel.
        If e.RowIndex = -1 AndAlso e.ColumnIndex = -1 Then
            If e.Button = MouseButtons.Left Then
                SelectAllCellsClicked(sender, EventArgs.Empty)
            End If
            Exit Sub
        End If

        'Chuột phải trên tiêu đề cột: chọn cột trước khi mở menu.
        If e.RowIndex = -1 AndAlso e.ColumnIndex >= 0 Then
            If e.Button = MouseButtons.Right Then
                SelectColumnRange(e.ColumnIndex, e.ColumnIndex, False)
                Grid.CurrentCell = FirstVisibleCellInColumn(e.ColumnIndex)
            End If
            Exit Sub
        End If

        'Chuột phải trên số hàng: chọn hàng trước khi mở menu.
        If e.ColumnIndex = -1 AndAlso e.RowIndex >= 0 Then
            If e.Button = MouseButtons.Right Then
                If Grid.SelectionMode <> DataGridViewSelectionMode.FullRowSelect Then
                    Grid.SelectionMode = DataGridViewSelectionMode.FullRowSelect
                    Grid.MultiSelect = True
                End If
                Grid.ClearSelection()
                Grid.Rows(e.RowIndex).Selected = True
                Grid.CurrentCell = FirstVisibleCellInRow(e.RowIndex)
            End If
            Exit Sub
        End If

        If e.RowIndex < 0 Then Exit Sub

        Dim row As DataGridViewRow = Grid.Rows(e.RowIndex)
        If e.ColumnIndex >= 0 Then Grid.CurrentCell = row.Cells(e.ColumnIndex)

        'Chuột phải một lần: chọn dòng để Context Menu hiển thị đúng Part.
        If e.Button = System.Windows.Forms.MouseButtons.Right Then
            If e.Clicks = 1 Then
                'Nếu dòng chưa thuộc vùng chọn thì chọn riêng dòng đó.
                'Nếu đã chọn nhiều dòng thì giữ nguyên vùng chọn để Context Menu tác động hàng loạt.
                If Not row.Selected Then
                    Grid.ClearSelection()
                    row.Selected = True
                End If
                If e.ColumnIndex >= 0 Then Grid.CurrentCell = row.Cells(e.ColumnIndex)
            End If
            Exit Sub
        End If

        If e.Button <> System.Windows.Forms.MouseButtons.Left Then Exit Sub

        'Không xử lý Double Click tại MouseDown để tránh chạy trùng sự kiện.
        'GridCellDoubleClick chịu trách nhiệm mở Part/Assembly/Drawing.
        'CellSelect cho phép chọn vùng như Excel; click Row Header tự chuyển sang FullRowSelect thật sự.
    End Sub

    'Chuột phải hai lần: bật/tắt chữ đậm cho toàn bộ dòng.
    Private Sub GridCellMouseDoubleClick(ByVal sender As Object, ByVal e As DataGridViewCellMouseEventArgs)
        If e.RowIndex < 0 Then Exit Sub
        If e.Button <> System.Windows.Forms.MouseButtons.Right Then Exit Sub

        Dim row As DataGridViewRow = Grid.Rows(e.RowIndex)
        If row.Tag Is Nothing Then Exit Sub

        Try
            If ContextMenu IsNot Nothing Then ContextMenu.Hide()
        Catch
        End Try

        Dim currentFont As Font = row.DefaultCellStyle.Font
        If currentFont Is Nothing Then currentFont = Grid.DefaultCellStyle.Font

        Dim isBold As Boolean = False
        If currentFont IsNot Nothing Then isBold = currentFont.Bold

        Dim baseFont As Font = Grid.DefaultCellStyle.Font
        If baseFont Is Nothing Then baseFont = New Font("Segoe UI", 9.0F, FontStyle.Regular)

        If isBold Then
            row.DefaultCellStyle.Font = New Font(baseFont.FontFamily, baseFont.Size, FontStyle.Regular)
        Else
            row.DefaultCellStyle.Font = New Font(baseFont.FontFamily, baseFont.Size, FontStyle.Bold)
        End If

        Grid.ClearSelection()
        row.Selected = True
        If e.ColumnIndex >= 0 Then Grid.CurrentCell = row.Cells(e.ColumnIndex)
    End Sub

    'Chuột trái một lần: chỉ chọn dòng.
    'Chọn dòng chỉ chọn dữ liệu; KHÔNG Highlight Part trong Assembly.
    Private Sub GridCellClick(ByVal sender As Object, ByVal e As DataGridViewCellEventArgs)
        If e.RowIndex < 0 OrElse e.ColumnIndex < 0 Then Exit Sub
        Dim row As DataGridViewRow = Grid.Rows(e.RowIndex)

        'CellSelect tự xử lý chọn ô/vùng, Ctrl và Shift.
        'Không ClearSelection ở đây vì sẽ phá chọn nhiều dòng.
        If Grid.CurrentCell Is Nothing OrElse Grid.CurrentCell.RowIndex <> e.RowIndex OrElse Grid.CurrentCell.ColumnIndex <> e.ColumnIndex Then
            Grid.CurrentCell = row.Cells(e.ColumnIndex)
        End If

        If IsAssemblyHeaderRow(row) Then
            If Grid.Columns.Contains("ITEM") AndAlso e.ColumnIndex = Grid.Columns("ITEM").Index Then
                ToggleGroup(GetRowGroupName(row))
            End If
            Exit Sub
        End If

        'Click đơn: CHỈ chọn dòng/cập nhật UI.
        'Không gọi Inventor Highlight ở đây để tránh lag.
    End Sub

    'Chuột trái hai lần:
    ' - Cột DRAWING: mở Drawing.
    ' - Ô iProperty có thể sửa: vào chế độ chỉnh sửa.
    ' - Các ô Part còn lại: mở Part.
    Private Sub GridCellDoubleClick(ByVal sender As Object, ByVal e As DataGridViewCellEventArgs)
        If e.RowIndex < 0 OrElse e.ColumnIndex < 0 Then Exit Sub
        Dim row As DataGridViewRow = Grid.Rows(e.RowIndex)
        Grid.CurrentCell = row.Cells(e.ColumnIndex)
        If Not row.Selected Then row.Selected = True

        If IsAssemblyHeaderRow(row) Then
            OpenAssemblySelected()
            Exit Sub
        End If

        Dim columnName As String = Grid.Columns(e.ColumnIndex).Name
        If String.Equals(columnName, "DRAWING_STATUS", StringComparison.OrdinalIgnoreCase) OrElse _
           String.Equals(columnName, "DRAWING", StringComparison.OrdinalIgnoreCase) Then
            OpenDrawing(TryCast(row.Tag, PartBomItem))
            Exit Sub
        End If

        'Double Click trái trên bất kỳ ô Part nào, kể cả ảnh Thumbnail: mở Part.
        OpenPart(TryCast(row.Tag, PartBomItem))
    End Sub

    Private Function IsPartNumberColumn(ByVal col As DataGridViewColumn) As Boolean
        If col Is Nothing Then Return False
        Dim propertyInfo As PropertyColumnInfo = TryCast(col.Tag, PropertyColumnInfo)
        If propertyInfo Is Nothing Then Return False
        Return String.Equals(propertyInfo.PropertyName.Trim(), "Part Number", StringComparison.OrdinalIgnoreCase)
    End Function

    Private Sub GridSelectionChanged(ByVal sender As Object, ByVal e As EventArgs)
        UpdatePreviewFromCurrentRow()
        ApplyCommandAvailability()
        UpdateExcelFormulaBar()
        UpdateExcelSelectionStatus()
        'MANUAL HIGHLIGHT ONLY: chọn dòng không truy cập Inventor API.
    End Sub

    Private Sub SelectionTimerTick(ByVal sender As Object, ByVal e As EventArgs)
        If _selectionTimer IsNot Nothing Then _selectionTimer.Stop()
        'MANUAL HIGHLIGHT ONLY: tuyệt đối không Highlight từ SelectionChanged/CellClick.
    End Sub


'####################################################################
' SUBSECTION 15.10 - CELL EDIT / UNDO / REDO / PROPERTY WRITE
'####################################################################

    Private Sub GridCellBeginEdit(ByVal sender As Object, ByVal e As DataGridViewCellCancelEventArgs)
        If _safeMode Then
            e.Cancel = True
            ShowSafeModeNotice("Edit Property")
            Exit Sub
        End If
        _editOriginalValue = ""
        _editDocumentKey = ""
        _editPropertyKey = ""
        If e.RowIndex < 0 OrElse e.ColumnIndex < 0 Then Exit Sub
        Dim row As DataGridViewRow = Grid.Rows(e.RowIndex)
        Dim item As PartBomItem = TryCast(row.Tag, PartBomItem)
        Dim propertyInfo As PropertyColumnInfo = TryCast(Grid.Columns(e.ColumnIndex).Tag, PropertyColumnInfo)
        If item Is Nothing OrElse propertyInfo Is Nothing Then Exit Sub
        _editOriginalValue = Convert.ToString(row.Cells(e.ColumnIndex).Value)
        _editDocumentKey = item.DocumentKey
        _editPropertyKey = propertyInfo.Key
    End Sub

    Private Sub UndoClicked(ByVal sender As Object, ByVal e As EventArgs)
        If Not EnsureWriteAllowed("Undo") Then Exit Sub
        If _transactionUndo.Count > 0 Then
            Dim tx As BomTransaction = _transactionUndo.Pop()
            If ApplyCommittedTransaction(tx, True) Then _transactionRedo.Push(tx) Else _transactionUndo.Push(tx)
            Exit Sub
        End If
        If _undoStack.Count = 0 Then MessageBox.Show("Không có thay đổi nào để Undo.", "BOM TOOL PRO", MessageBoxButtons.OK, MessageBoxIcon.Information) : Exit Sub
        Dim action As BomEditAction = _undoStack.Pop()
        If ApplyHistoryAction(action, action.OldValue) Then _redoStack.Push(action)
    End Sub

    Private Sub RedoClicked(ByVal sender As Object, ByVal e As EventArgs)
        If Not EnsureWriteAllowed("Redo") Then Exit Sub
        If _transactionRedo.Count > 0 Then
            Dim tx As BomTransaction = _transactionRedo.Pop()
            If ApplyCommittedTransaction(tx, False) Then _transactionUndo.Push(tx) Else _transactionRedo.Push(tx)
            Exit Sub
        End If
        If _redoStack.Count = 0 Then MessageBox.Show("Không có thay đổi nào để Redo.", "BOM TOOL PRO", MessageBoxButtons.OK, MessageBoxIcon.Information) : Exit Sub
        Dim action As BomEditAction = _redoStack.Pop()
        If ApplyHistoryAction(action, action.NewValue) Then _undoStack.Push(action)
    End Sub

    Private Function ApplyCommittedTransaction(ByVal tx As BomTransaction, ByVal undoMode As Boolean) As Boolean
        If tx Is Nothing OrElse tx.Changes.Count = 0 Then Return False
        Dim done As New List(Of BomPropertyChange)()
        Try
            Dim ordered As New List(Of BomPropertyChange)(tx.Changes)
            If undoMode Then ordered.Reverse()
            For Each ch As BomPropertyChange In ordered
                If ch.Status <> "COMMITTED" AndAlso ch.Status <> "UNDONE" Then Continue For
                Dim item As PartBomItem = FindItemByDocumentKey(ch.DocumentKey)
                If item Is Nothing OrElse item.Document Is Nothing Then Throw New Exception("Không tìm thấy Document: " & ch.FileName)
                Dim value As String = If(undoMode, ch.OldValue, ch.NewValue)
                If undoMode AndAlso Not ch.PropertyExistedBefore Then
                    DeletePropertyIfExists(item.Document, ch.PropertyInfo)
                Else
                    WritePropertyValue(item.Document, ch.PropertyInfo, value)
                End If
                item.SelectedPropertyValues(ch.PropertyKey) = value : item.IsBomDirty = True : item.DirtyPropertyKeys.Add(ch.PropertyKey)
                If String.Equals(ch.PropertyInfo.PropertyName, "Part Number", StringComparison.OrdinalIgnoreCase) Then item.PartNumber = value
                RebuildItemSearchBlob(item) : _committedDocumentKeys.Add(ch.DocumentKey) : done.Add(ch)
            Next
            For Each ch As BomPropertyChange In tx.Changes : ch.Status = If(undoMode, "UNDONE", "COMMITTED") : Next
            RefreshGridAfterTransaction()
            MessageBox.Show(If(undoMode, "UNDO", "REDO") & " TRANSACTION: " & tx.Name & vbCrLf & done.Count.ToString() & " thay đổi.", "BOM TRANSACTION", MessageBoxButtons.OK, MessageBoxIcon.Information)
            Return True
        Catch ex As Exception
            MessageBox.Show("Không thể " & If(undoMode, "Undo", "Redo") & " transaction." & vbCrLf & ex.Message, "BOM TRANSACTION", MessageBoxButtons.OK, MessageBoxIcon.Error)
            Return False
        End Try
    End Function

    Private Function ApplyHistoryAction(ByVal action As BomEditAction, ByVal targetValue As String) As Boolean
        If action Is Nothing OrElse action.PropertyInfo Is Nothing Then Return False
        Dim item As PartBomItem = Nothing
        For Each candidate As PartBomItem In _allItems
            If String.Equals(candidate.DocumentKey, action.DocumentKey, StringComparison.OrdinalIgnoreCase) Then
                item = candidate
                Exit For
            End If
        Next
        If item Is Nothing Then Return False
        Try
            _suppressCellWrite = True
            WritePropertyValue(item.Document, action.PropertyInfo, targetValue)
            item.SelectedPropertyValues(action.PropertyKey) = targetValue
            If String.Equals(action.PropertyInfo.PropertyName, "Part Number", StringComparison.OrdinalIgnoreCase) Then item.PartNumber = targetValue
            For Each row As DataGridViewRow In Grid.Rows
                Dim rowItem As PartBomItem = TryCast(row.Tag, PartBomItem)
                If rowItem IsNot Nothing AndAlso String.Equals(rowItem.DocumentKey, item.DocumentKey, StringComparison.OrdinalIgnoreCase) Then
                    For Each col As DataGridViewColumn In Grid.Columns
                        Dim pi As PropertyColumnInfo = TryCast(col.Tag, PropertyColumnInfo)
                        If pi IsNot Nothing AndAlso String.Equals(pi.Key, action.PropertyKey, StringComparison.OrdinalIgnoreCase) Then
                            row.Cells(col.Index).Value = targetValue
                            Exit For
                        End If
                    Next
                    If Grid.Columns.Contains("DATA_STATUS") Then row.Cells("DATA_STATUS").Value = GetDataStatus(item)
                End If
            Next
            _suppressCellWrite = False
            Return True
        Catch ex As Exception
            _suppressCellWrite = False
            MessageBox.Show("Không thể áp dụng Undo/Redo." & vbCrLf & ex.Message, "BOM TOOL PRO", MessageBoxButtons.OK, MessageBoxIcon.Error)
            Return False
        End Try
    End Function

    Private Sub GridCellEndEdit(ByVal sender As Object, ByVal e As DataGridViewCellEventArgs)
        If _suppressCellWrite OrElse e.RowIndex < 0 OrElse e.ColumnIndex < 0 Then Exit Sub
        Dim row As DataGridViewRow = Grid.Rows(e.RowIndex)
        Dim item As PartBomItem = TryCast(row.Tag, PartBomItem)
        If item Is Nothing Then Exit Sub
        Dim col As DataGridViewColumn = Grid.Columns(e.ColumnIndex)
        Dim propertyInfo As PropertyColumnInfo = TryCast(col.Tag, PropertyColumnInfo)
        If propertyInfo Is Nothing OrElse col.ReadOnly Then Exit Sub
        Dim newValue As String = Convert.ToString(row.Cells(e.ColumnIndex).Value)
        If String.Equals(_editOriginalValue, newValue, StringComparison.Ordinal) Then Exit Sub
        StagePropertyChange(item, propertyInfo, _editOriginalValue, newValue, row, e.ColumnIndex)
    End Sub

    Private Sub StagePropertyChange(ByVal item As PartBomItem, ByVal propertyInfo As PropertyColumnInfo, ByVal oldValue As String, ByVal newValue As String, ByVal row As DataGridViewRow, ByVal columnIndex As Integer)
        If item Is Nothing OrElse propertyInfo Is Nothing Then Exit Sub
        Dim existing As BomPropertyChange = Nothing
        For Each ch As BomPropertyChange In _pendingTransaction.Changes
            If String.Equals(ch.DocumentKey, item.DocumentKey, StringComparison.OrdinalIgnoreCase) AndAlso String.Equals(ch.PropertyKey, propertyInfo.Key, StringComparison.OrdinalIgnoreCase) Then existing = ch : Exit For
        Next
        If existing Is Nothing Then
            existing = New BomPropertyChange()
            existing.DocumentKey = item.DocumentKey
            existing.DocumentPath = item.FilePath
            existing.PartNumber = item.PartNumber
            existing.FileName = item.FileName
            existing.PropertyKey = propertyInfo.Key
            existing.PropertyInfo = propertyInfo
            existing.OldValue = oldValue
            existing.PropertyExistedBefore = PropertyExistsInDocument(item.Document, propertyInfo)
            _pendingTransaction.Changes.Add(existing)
        End If
        existing.NewValue = newValue
        existing.Status = "PENDING"
        existing.ErrorMessage = ""
        If String.Equals(existing.OldValue, existing.NewValue, StringComparison.Ordinal) Then _pendingTransaction.Changes.Remove(existing)
        _pendingTransaction.Status = If(_pendingTransaction.Changes.Count > 0, "PENDING", "EMPTY")
        If row IsNot Nothing AndAlso columnIndex >= 0 Then
            row.Cells(columnIndex).Style.BackColor = Color.FromArgb(255, 248, 200)
            row.Cells(columnIndex).ToolTipText = "PENDING - chưa ghi vào Inventor. REVIEW / COMMIT / DISCARD."
            If Grid.Columns.Contains("DATA_STATUS") Then row.Cells("DATA_STATUS").Value = "PENDING CHANGES"
        End If
        PersistPendingTransaction()
        UpdatePendingCaption()
    End Sub

    Private Sub UpdatePendingCaption()
        Dim n As Integer = _pendingTransaction.Changes.Count
        Me.Text = BomConstants.ToolVersion & " - " & _assemblyName & If(n > 0, "  |  " & n.ToString() & " PENDING", "")
        If StatusPending IsNot Nothing Then
            StatusPending.Text = n.ToString() & " Pending"
            StatusPending.ForeColor = If(n > 0, Color.DarkOrange, Color.FromArgb(55, 80, 90))
        End If
        If _quickButtons.ContainsKey("REVIEW") Then
            Dim rb As Button = _quickButtons("REVIEW")
            rb.Text = "REVIEW [" & n.ToString() & "]"
            rb.ForeColor = If(n > 0, Color.DarkOrange, Color.FromArgb(40, 70, 85))
        End If
    End Sub

    Private Sub ReviewPendingClicked(ByVal sender As Object, ByVal e As EventArgs)
        If _pendingTransaction.Changes.Count = 0 Then
            MessageBox.Show("Không có Pending Changes.", "BOM TOOL PRO", MessageBoxButtons.OK, MessageBoxIcon.Information)
            Exit Sub
        End If
        Using f As New BomPendingChangesForm(_pendingTransaction.Changes)
            If f.ShowDialog(Me) = DialogResult.OK Then
                If f.ActionName = "COMMIT_SELECTED" Then
                    CommitChanges(f.SelectedChanges, False, _transactionAtomic, "COMMIT SELECTED")
                ElseIf f.ActionName = "COMMIT_ALL" Then
                    CommitChanges(New List(Of BomPropertyChange)(_pendingTransaction.Changes), False, _transactionAtomic, "COMMIT ALL")
                ElseIf f.ActionName = "DISCARD_SELECTED" Then
                    DiscardSpecificPendingChanges(f.SelectedChanges)
                ElseIf f.ActionName = "DISCARD_ALL" Then
                    DiscardPendingClicked(Nothing, EventArgs.Empty)
                End If
            End If
        End Using
    End Sub

    Private Sub CommitPendingClicked(ByVal sender As Object, ByVal e As EventArgs)
        If _safeMode Then ShowSafeModeNotice("CommitPendingClicked") : Exit Sub
        CommitChanges(New List(Of BomPropertyChange)(_pendingTransaction.Changes), False, _transactionAtomic, "COMMIT ALL")
    End Sub

    Private Sub CommitSelectedClicked(ByVal sender As Object, ByVal e As EventArgs)
        If _safeMode Then ShowSafeModeNotice("CommitSelectedClicked") : Exit Sub
        Dim selected As List(Of BomPropertyChange) = GetSelectedPendingChanges()
        If selected.Count = 0 Then
            MessageBox.Show("Không có Pending Change nào trong vùng đang chọn.", "BOM TRANSACTION", MessageBoxButtons.OK, MessageBoxIcon.Information)
            Exit Sub
        End If
        CommitChanges(selected, False, _transactionAtomic, "COMMIT SELECTED")
    End Sub

    Private Function GetSelectedPendingChanges() As List(Of BomPropertyChange)
        Dim result As New List(Of BomPropertyChange)()
        Dim keys As New HashSet(Of String)(StringComparer.OrdinalIgnoreCase)
        For Each cell As System.Windows.Forms.DataGridViewCell In Grid.SelectedCells
            If cell.RowIndex < 0 OrElse cell.ColumnIndex < 0 Then Continue For
            Dim item As PartBomItem = TryCast(Grid.Rows(cell.RowIndex).Tag, PartBomItem)
            Dim pi As PropertyColumnInfo = TryCast(Grid.Columns(cell.ColumnIndex).Tag, PropertyColumnInfo)
            If item Is Nothing OrElse pi Is Nothing Then Continue For
            keys.Add(item.DocumentKey & "|" & pi.Key)
        Next
        If keys.Count = 0 AndAlso Grid.CurrentCell IsNot Nothing Then
            Dim item As PartBomItem = TryCast(Grid.Rows(Grid.CurrentCell.RowIndex).Tag, PartBomItem)
            Dim pi As PropertyColumnInfo = TryCast(Grid.Columns(Grid.CurrentCell.ColumnIndex).Tag, PropertyColumnInfo)
            If item IsNot Nothing AndAlso pi IsNot Nothing Then keys.Add(item.DocumentKey & "|" & pi.Key)
        End If
        For Each ch As BomPropertyChange In _pendingTransaction.Changes
            If keys.Contains(ch.DocumentKey & "|" & ch.PropertyKey) Then result.Add(ch)
        Next
        Return result
    End Function

    Private Function CloneTransaction(ByVal changes As List(Of BomPropertyChange), ByVal name As String) As BomTransaction
        Dim tx As New BomTransaction()
        tx.Name = name
        tx.Atomic = _transactionAtomic
        For Each source As BomPropertyChange In changes
            Dim ch As New BomPropertyChange()
            ch.DocumentKey = source.DocumentKey : ch.FileName = source.FileName : ch.PropertyKey = source.PropertyKey
            ch.PropertyInfo = source.PropertyInfo : ch.OldValue = source.OldValue : ch.NewValue = source.NewValue
            ch.PropertyExistedBefore = source.PropertyExistedBefore
            ch.Status = source.Status : ch.ErrorMessage = source.ErrorMessage
            tx.Changes.Add(ch)
        Next
        Return tx
    End Function

    Private Function CommitChanges(ByVal requested As List(Of BomPropertyChange), ByVal saveAfterCommit As Boolean, ByVal atomic As Boolean, ByVal transactionName As String) As Boolean
        If Not EnsureWriteAllowed(transactionName) Then Return False
        If requested Is Nothing OrElse requested.Count = 0 Then Return True
        Dim answer As DialogResult = MessageBox.Show(transactionName & ": " & requested.Count.ToString() & " thay đổi?" & vbCrLf & "Atomic = " & If(atomic, "ON (lỗi sẽ rollback)", "OFF (cho phép Partial Commit)"), "BOM TRANSACTION", MessageBoxButtons.YesNo, MessageBoxIcon.Question)
        If answer <> DialogResult.Yes Then Return False
        Dim tx As BomTransaction = CloneTransaction(requested, transactionName)
        tx.Atomic = atomic
        Dim applied As New List(Of BomPropertyChange)()
        Dim failure As Exception = Nothing
        For i As Integer = 0 To tx.Changes.Count - 1
            Dim ch As BomPropertyChange = tx.Changes(i)
            Try
                Dim item As PartBomItem = FindItemByDocumentKey(ch.DocumentKey)
                If item Is Nothing OrElse item.Document Is Nothing Then Throw New Exception("Không tìm thấy Document: " & ch.FileName)
                'Nếu property được một thao tác khác tạo sau lúc Stage nhưng trước Commit, coi nó là property có sẵn để Undo không xóa nhầm.
                If Not ch.PropertyExistedBefore AndAlso PropertyExistsInDocument(item.Document, ch.PropertyInfo) Then ch.PropertyExistedBefore = True
                WritePropertyValue(item.Document, ch.PropertyInfo, ch.NewValue)
                ch.Status = "COMMITTED" : applied.Add(ch) : tx.AppliedCount += 1
                _committedDocumentKeys.Add(ch.DocumentKey)
            Catch ex As Exception
                ch.Status = "FAILED" : ch.ErrorMessage = ex.Message : tx.FailedCount += 1
                tx.NotProcessedCount = tx.Changes.Count - i - 1
                failure = ex
                If atomic Then Exit For
            End Try
        Next
        If failure IsNot Nothing AndAlso atomic Then
            For i As Integer = applied.Count - 1 To 0 Step -1
                Dim ch As BomPropertyChange = applied(i)
                Try
                    Dim item As PartBomItem = FindItemByDocumentKey(ch.DocumentKey)
                    If item Is Nothing OrElse item.Document Is Nothing Then Throw New Exception("Document unavailable")
                    If ch.PropertyExistedBefore Then
                        WritePropertyValue(item.Document, ch.PropertyInfo, ch.OldValue)
                    Else
                        DeletePropertyIfExists(item.Document, ch.PropertyInfo)
                    End If
                    ch.Status = "ROLLED BACK"
                    _committedDocumentKeys.Remove(ch.DocumentKey)
                Catch rbEx As Exception
                    ch.Status = "ROLLBACK FAILED" : ch.ErrorMessage = rbEx.Message : tx.RollbackFailedCount += 1
                End Try
            Next
            tx.Status = If(tx.RollbackFailedCount = 0, "ROLLED BACK", "PARTIAL COMMIT")
            MessageBox.Show("TRANSACTION FAILED" & vbCrLf & "Successful before error: " & tx.AppliedCount.ToString() & vbCrLf & "Failed: " & tx.FailedCount.ToString() & vbCrLf & "Not processed: " & tx.NotProcessedCount.ToString() & vbCrLf & "Rollback failed: " & tx.RollbackFailedCount.ToString() & vbCrLf & vbCrLf & failure.Message, "BOM TRANSACTION", MessageBoxButtons.OK, MessageBoxIcon.Error)
            Return False
        End If
        For Each ch As BomPropertyChange In tx.Changes
            If ch.Status <> "COMMITTED" Then Continue For
            Dim item As PartBomItem = FindItemByDocumentKey(ch.DocumentKey)
            If item Is Nothing Then Continue For
            item.SelectedPropertyValues(ch.PropertyKey) = ch.NewValue : item.IsBomDirty = True : item.DirtyPropertyKeys.Add(ch.PropertyKey)
            If String.Equals(ch.PropertyInfo.PropertyName, "Part Number", StringComparison.OrdinalIgnoreCase) Then item.PartNumber = ch.NewValue
            RebuildItemSearchBlob(item)
            For i As Integer = _pendingTransaction.Changes.Count - 1 To 0 Step -1
                Dim p As BomPropertyChange = _pendingTransaction.Changes(i)
                If String.Equals(p.DocumentKey, ch.DocumentKey, StringComparison.OrdinalIgnoreCase) AndAlso String.Equals(p.PropertyKey, ch.PropertyKey, StringComparison.OrdinalIgnoreCase) Then _pendingTransaction.Changes.RemoveAt(i)
            Next
        Next
        tx.Status = If(tx.FailedCount = 0, "COMMITTED", "PARTIAL COMMIT")
        If tx.AppliedCount > 0 Then _transactionUndo.Push(tx) : _transactionRedo.Clear()
        RefreshGridAfterTransaction() : UpdatePendingCaption()
        If saveAfterCommit Then SaveChangedDocumentsCore()
        MessageBox.Show(tx.Status & vbCrLf & "Committed: " & tx.AppliedCount.ToString() & vbCrLf & "Failed: " & tx.FailedCount.ToString() & vbCrLf & "Remaining Pending: " & _pendingTransaction.Changes.Count.ToString(), "BOM TRANSACTION", MessageBoxButtons.OK, If(tx.FailedCount = 0, MessageBoxIcon.Information, MessageBoxIcon.Warning))
        Return tx.FailedCount = 0
    End Function

    Public Function ResolvePendingBeforeAssemblySwitch() As Boolean
        If _pendingTransaction Is Nothing OrElse _pendingTransaction.Changes Is Nothing OrElse _pendingTransaction.Changes.Count = 0 Then Return True

        Do While _pendingTransaction IsNot Nothing AndAlso _pendingTransaction.Changes IsNot Nothing AndAlso _pendingTransaction.Changes.Count > 0
            Using f As New BomPendingSwitchForm(_pendingTransaction.Changes.Count, _assemblyName)
                f.ShowDialog(Me)
                Select Case f.Decision
                    Case BomPendingSwitchDecision.Cancel
                        Return False

                    Case BomPendingSwitchDecision.Review
                        ReviewPendingClicked(Nothing, EventArgs.Empty)
                        'Review may commit/discard some or all changes. If some remain, ask again.

                    Case BomPendingSwitchDecision.Commit
                        If Not CommitPendingChanges(False) Then Return False

                    Case BomPendingSwitchDecision.Discard
                        For Each ch As BomPropertyChange In New List(Of BomPropertyChange)(_pendingTransaction.Changes)
                            RestoreGridPendingValue(ch, ch.OldValue)
                        Next
                        _pendingTransaction = New BomTransaction()
                        UpdatePendingCaption()
                        SaveSessionState()

                    Case Else
                        Return False
                End Select
            End Using
        Loop

        Return True
    End Function

    Private Function CommitPendingChanges(ByVal saveAfterCommit As Boolean) As Boolean
        Return CommitChanges(New List(Of BomPropertyChange)(_pendingTransaction.Changes), saveAfterCommit, _transactionAtomic, "COMMIT ALL")
    End Function

    Private Function FindItemByDocumentKey(ByVal key As String) As PartBomItem
        For Each item As PartBomItem In _allItems
            If String.Equals(item.DocumentKey, key, StringComparison.OrdinalIgnoreCase) Then Return item
        Next
        Return Nothing
    End Function

    Private Sub DiscardPendingClicked(ByVal sender As Object, ByVal e As EventArgs)
        If _pendingTransaction.Changes.Count = 0 Then Exit Sub
        If MessageBox.Show("Hủy " & _pendingTransaction.Changes.Count.ToString() & " Pending Changes? Inventor chưa bị thay đổi.", "DISCARD", MessageBoxButtons.YesNo, MessageBoxIcon.Question) <> DialogResult.Yes Then Exit Sub
        For Each ch As BomPropertyChange In _pendingTransaction.Changes
            RestoreGridPendingValue(ch, ch.OldValue)
        Next
        _pendingTransaction = New BomTransaction()
        UpdatePendingCaption()
    End Sub

    Private Sub RestoreGridPendingValue(ByVal ch As BomPropertyChange, ByVal value As String)
        _suppressCellWrite = True
        For Each row As DataGridViewRow In Grid.Rows
            Dim item As PartBomItem = TryCast(row.Tag, PartBomItem)
            If item Is Nothing OrElse Not String.Equals(item.DocumentKey, ch.DocumentKey, StringComparison.OrdinalIgnoreCase) Then Continue For
            For Each col As DataGridViewColumn In Grid.Columns
                Dim pi As PropertyColumnInfo = TryCast(col.Tag, PropertyColumnInfo)
                If pi IsNot Nothing AndAlso String.Equals(pi.Key, ch.PropertyKey, StringComparison.OrdinalIgnoreCase) Then
                    row.Cells(col.Index).Value = value
                    row.Cells(col.Index).Style.BackColor = Color.White
                    row.Cells(col.Index).ToolTipText = ""
                End If
            Next
            If Grid.Columns.Contains("DATA_STATUS") Then row.Cells("DATA_STATUS").Value = GetDataStatus(item)
        Next
        _suppressCellWrite = False
    End Sub

    Private Sub RefreshGridAfterTransaction()
        _suppressCellWrite = True
        For Each row As DataGridViewRow In Grid.Rows
            Dim item As PartBomItem = TryCast(row.Tag, PartBomItem)
            If item Is Nothing Then Continue For
            For Each col As DataGridViewColumn In Grid.Columns
                Dim pi As PropertyColumnInfo = TryCast(col.Tag, PropertyColumnInfo)
                If pi IsNot Nothing AndAlso item.SelectedPropertyValues.ContainsKey(pi.Key) Then
                    row.Cells(col.Index).Value = item.SelectedPropertyValues(pi.Key)
                    row.Cells(col.Index).Style.BackColor = Color.White
                    row.Cells(col.Index).ToolTipText = ""
                End If
            Next
            If Grid.Columns.Contains("DATA_STATUS") Then row.Cells("DATA_STATUS").Value = GetDataStatus(item)
        Next
        _suppressCellWrite = False
    End Sub

    Private Const UserDefinedPropertySetInternalName As String = "{D5CDD505-2E9C-101B-9397-08002B2CF9AE}"
    Private Const UserDefinedPropertySetName As String = "Inventor User Defined Properties"

    Private Function IsUserDefinedProperty(ByVal propertyInfo As PropertyColumnInfo) As Boolean
        If propertyInfo Is Nothing Then Return False
        If String.Equals(propertyInfo.PropertySetInternalName, UserDefinedPropertySetInternalName, StringComparison.OrdinalIgnoreCase) Then Return True
        If String.Equals(propertyInfo.PropertySetDisplayName, "User Defined Properties", StringComparison.OrdinalIgnoreCase) Then Return True
        If String.Equals(propertyInfo.PropertySetDisplayName, UserDefinedPropertySetName, StringComparison.OrdinalIgnoreCase) Then Return True
        Return False
    End Function

    Private Function GetPropertySetSafe(ByVal doc As Inventor.Document, ByVal propertyInfo As PropertyColumnInfo) As Inventor.PropertySet
        If doc Is Nothing OrElse propertyInfo Is Nothing Then Return Nothing
        Try
            Return doc.PropertySets.Item(propertyInfo.PropertySetInternalName)
        Catch
            If IsUserDefinedProperty(propertyInfo) Then
                Try
                    Return doc.PropertySets.Item(UserDefinedPropertySetName)
                Catch
                End Try
            End If
        End Try
        Return Nothing
    End Function

    Private Function PropertyExistsInDocument(ByVal doc As Inventor.Document, ByVal propertyInfo As PropertyColumnInfo) As Boolean
        If doc Is Nothing OrElse propertyInfo Is Nothing Then Return False
        If propertyInfo.IsSystemSetting Then Return True
        Dim setObj As Inventor.PropertySet = GetPropertySetSafe(doc, propertyInfo)
        If setObj Is Nothing Then Return False
        Try
            Dim prop As Inventor.Property = setObj.Item(propertyInfo.PropertyName)
            Return prop IsNot Nothing
        Catch
            Return False
        End Try
    End Function

    Private Sub DeletePropertyIfExists(ByVal doc As Inventor.Document, ByVal propertyInfo As PropertyColumnInfo)
        If doc Is Nothing OrElse propertyInfo Is Nothing Then Exit Sub
        If Not IsUserDefinedProperty(propertyInfo) Then Throw New InvalidOperationException("Chỉ Custom iProperty mới được phép xóa khi Undo/Rollback.")
        Dim setObj As Inventor.PropertySet = GetPropertySetSafe(doc, propertyInfo)
        If setObj Is Nothing Then Exit Sub
        Try
            Dim prop As Inventor.Property = setObj.Item(propertyInfo.PropertyName)
            If prop IsNot Nothing Then prop.Delete()
        Catch
            'Không tồn tại = trạng thái rollback mong muốn.
        End Try
    End Sub

    Private Sub WritePropertyValue(ByVal doc As Inventor.Document, ByVal propertyInfo As PropertyColumnInfo, ByVal newValue As String)
        If Not EnsureWriteAllowed("Write iProperty") Then Throw New InvalidOperationException("SAFE MODE: Write blocked.")
        If doc Is Nothing Then Throw New Exception("Không còn kết nối tới tài liệu Part.")
        If propertyInfo Is Nothing OrElse String.IsNullOrWhiteSpace(propertyInfo.PropertyName) Then Throw New Exception("Thông tin iProperty không hợp lệ.")

        If propertyInfo.IsSystemSetting Then
            WriteSystemSettingValue(doc, propertyInfo, newValue)
            Exit Sub
        End If

        Dim setObj As Inventor.PropertySet = GetPropertySetSafe(doc, propertyInfo)
        If setObj Is Nothing Then Throw New Exception("Không tìm thấy PropertySet: " & propertyInfo.PropertySetDisplayName)

        Dim prop As Inventor.Property = Nothing
        Try
            prop = setObj.Item(propertyInfo.PropertyName)
        Catch
            prop = Nothing
        End Try

        If prop Is Nothing Then
            If Not IsUserDefinedProperty(propertyInfo) Then
                Throw New Exception("iProperty '" & propertyInfo.PropertyName & "' chưa tồn tại và không phải Custom iProperty nên không thể tự tạo.")
            End If
            'Autodesk Inventor API: Custom iProperty được tạo bằng PropertySet.Add(value, name).
            setObj.Add(CObj(If(newValue, "")), propertyInfo.PropertyName)
        Else
            prop.Value = newValue
        End If
        'Không Update2 sau từng ô: đây là một COM/API operation rất đắt.
        'Document đã tự chuyển sang Dirty; Update/Save được gom theo lệnh người dùng.
    End Sub

    Private Sub RebuildItemSearchBlob(ByVal item As PartBomItem)
        If item Is Nothing Then Exit Sub
        item.SearchBlob = (item.FileName & "|" & item.FilePath & "|" & item.PartNumber & "|" & item.Description & "|" & item.Material & "|" & item.Vendor & "|" & item.Revision & "|" & item.StockNumber & "|" & item.Project & "|" & item.Category & "|" & item.GetParentAssemblyText()).ToUpperInvariant()
        For Each kv As KeyValuePair(Of String, Object) In item.SelectedPropertyValues
            item.SearchBlob &= "|" & Convert.ToString(kv.Value).ToUpperInvariant()
        Next
    End Sub

    Private Sub GridDataError(ByVal sender As Object, ByVal e As System.Windows.Forms.DataGridViewDataErrorEventArgs)
        e.ThrowException = False
    End Sub


'####################################################################
' SUBSECTION 15.11 - PROPERTY COMMANDS / SAVE / DASHBOARD / CHECK
'####################################################################

    Private Sub BeginEditPropertyClicked(ByVal sender As Object, ByVal e As EventArgs)
        If Not EnsureWriteAllowed("Edit Property") Then Exit Sub
        If Grid.CurrentCell Is Nothing Then Exit Sub
        If Grid.CurrentRow Is Nothing OrElse Grid.CurrentRow.Tag Is Nothing Then Exit Sub
        If Grid.CurrentCell.OwningColumn.ReadOnly Then
            MessageBox.Show("Cột này không phải iProperty có thể chỉnh sửa.", "BOM TOOL PRO", MessageBoxButtons.OK, MessageBoxIcon.Information)
            Exit Sub
        End If
        Grid.BeginEdit(True)
    End Sub

    Private Sub AddPropertiesClicked(ByVal sender As Object, ByVal e As EventArgs)
        Dim propertyDictionary As New Dictionary(Of String, PropertyColumnInfo)(StringComparer.OrdinalIgnoreCase)
        Me.Cursor = System.Windows.Forms.Cursors.WaitCursor
        Try
            For Each item As PartBomItem In _allItems
                If item.Document IsNot Nothing Then ScanDocumentPropertyNames(item.Document, propertyDictionary)
            Next
        Finally
            Me.Cursor = System.Windows.Forms.Cursors.Default
        End Try

        Dim available As New List(Of PropertyColumnInfo)()
        For Each pair As KeyValuePair(Of String, PropertyColumnInfo) In propertyDictionary
            Dim alreadySelected As Boolean = False
            For Each selected As PropertyColumnInfo In _selectedProperties
                If String.Equals(selected.Key, pair.Key, StringComparison.OrdinalIgnoreCase) Then alreadySelected = True : Exit For
            Next
            If Not alreadySelected Then available.Add(pair.Value)
        Next
        'Bổ sung các setting native của Part/Sheet Metal vào cùng bộ chọn cột.
        Dim systemCandidates As New List(Of PropertyColumnInfo)()
        AddUniversalSystemSettings(systemCandidates)
        For Each sys As PropertyColumnInfo In systemCandidates
            Dim alreadySelectedSystem As Boolean = False
            For Each selected As PropertyColumnInfo In _selectedProperties
                If String.Equals(selected.Key, sys.Key, StringComparison.OrdinalIgnoreCase) Then alreadySelectedSystem = True : Exit For
            Next
            If Not alreadySelectedSystem Then available.Add(sys)
        Next

        available.Sort(AddressOf ComparePropertyColumns)
        'Ngay cả khi không còn iProperty hiện có, vẫn mở form để người dùng tạo Custom iProperty mới.
        Dim picker As New BomAddPropertiesForm(available)
        If picker.ShowDialog(Me) <> DialogResult.OK OrElse picker.SelectedProperties.Count = 0 Then Exit Sub

        Me.Cursor = System.Windows.Forms.Cursors.WaitCursor
        Try
            For Each p As PropertyColumnInfo In picker.SelectedProperties
                Dim duplicate As Boolean = False
                For Each selected As PropertyColumnInfo In _selectedProperties
                    If selected IsNot Nothing AndAlso String.Equals(selected.Key, p.Key, StringComparison.OrdinalIgnoreCase) Then duplicate = True : Exit For
                Next
                If duplicate Then Continue For
                _selectedProperties.Add(p)
                For Each item As PartBomItem In _allItems
                    item.SelectedPropertyValues(p.Key) = ReadSingleSelectedProperty(item.Document, p)
                Next
                AddPropertyColumn(p)
            Next
            LoadRows()
        Finally
            Me.Cursor = System.Windows.Forms.Cursors.Default
        End Try
    End Sub

    Private Sub SaveChangedDocumentsClicked(ByVal sender As Object, ByVal e As EventArgs)
        If Not EnsureWriteAllowed("Save Changed Documents") Then Exit Sub
        If _pendingTransaction.Changes.Count > 0 Then
            MessageBox.Show("Có " & _pendingTransaction.Changes.Count.ToString() & " Pending Changes chưa COMMIT." & vbCrLf & "SAVE chỉ lưu các thay đổi đã Commit; Pending không được ghi vào Inventor.", "BOM TRANSACTION", MessageBoxButtons.OK, MessageBoxIcon.Warning)
        End If
        SaveChangedDocumentsCore()
    End Sub

    Private Sub SaveChangedDocumentsCore()
        Dim saved As Integer = 0
        Dim failed As New List(Of String)()
        Dim processed As New HashSet(Of String)(StringComparer.OrdinalIgnoreCase)
        For Each item As PartBomItem In _allItems
            Try
                If item.Document IsNot Nothing AndAlso _committedDocumentKeys.Contains(item.DocumentKey) AndAlso Not processed.Contains(item.DocumentKey) Then
                    processed.Add(item.DocumentKey)
                    If item.Document.Dirty Then item.Document.Save2(True)
                    item.IsBomDirty = False
                    item.DirtyPropertyKeys.Clear()
                    _committedDocumentKeys.Remove(item.DocumentKey)
                    saved += 1
                End If
            Catch ex As Exception
                failed.Add(item.FileName & ": " & ex.Message)
            End Try
        Next
        Dim msg As String = "Đã lưu " & saved.ToString() & " Document đã Commit."
        If failed.Count > 0 Then msg &= vbCrLf & vbCrLf & "Không lưu được:" & vbCrLf & String.Join(vbCrLf, failed.ToArray())
        MessageBox.Show(msg, "BOM TOOL PRO", MessageBoxButtons.OK, If(failed.Count = 0, MessageBoxIcon.Information, MessageBoxIcon.Warning))
    End Sub

    Private Sub DashboardClicked(ByVal sender As Object, ByVal e As EventArgs)
        Dim form As New BomDashboardForm(_allItems)
        form.ShowDialog(Me)
        form.Dispose()
    End Sub

    Public Sub StageValidationFix(ByVal result As BomValidationResult)
        If Not EnsureWriteAllowed("Auto Fix / Stage Validation") Then Exit Sub
        If result Is Nothing OrElse result.Item Is Nothing OrElse Not result.CanAutoFix Then Exit Sub
        Dim p As PropertyColumnInfo = result.FixPropertyInfo
        If p Is Nothing Then Exit Sub
        Dim oldValue As String = result.CurrentValue
        Dim newValue As String = result.SuggestedValue
        StagePropertyChange(result.Item, p, oldValue, newValue, Nothing, -1)
        If result.Item.SelectedPropertyValues IsNot Nothing Then result.Item.SelectedPropertyValues(p.Key) = newValue
        result.Status = "STAGED"
    End Sub

    Private Sub ProjectCheckClicked(ByVal sender As Object, ByVal e As EventArgs)
        Dim form As New BomProjectCheckForm(_allItems, AddressOf OpenPart, AddressOf GetDrawingStatus, AddressOf StageValidationFix)
        form.ShowDialog(Me)
        form.Dispose()
    End Sub


'####################################################################
' SUBSECTION 15.12 - DISPLAY MODE / GROUP / MARK / TABLE STATE
'####################################################################

    Private Sub GridLayoutChanged(ByVal sender As Object, ByVal e As EventArgs)
    End Sub

    Private Sub ToggleDisplayModeClicked(ByVal sender As Object, ByVal e As EventArgs)
        Select Case _bomDisplayMode
            Case BomDisplayMode.PartsOnly
                _bomDisplayMode = BomDisplayMode.Structured
            Case BomDisplayMode.Structured
                _bomDisplayMode = BomDisplayMode.Hybrid
            Case Else
                _bomDisplayMode = BomDisplayMode.PartsOnly
        End Select

        _groupedView = (_bomDisplayMode <> BomDisplayMode.PartsOnly)
        _collapsedGroups.Clear()

        If _displayModeButton IsNot Nothing Then
            Select Case _bomDisplayMode
                Case BomDisplayMode.PartsOnly
                    _displayModeButton.Text = "PARTS ONLY"
                    _displayModeButton.ToolTipText = "Danh sách Part phẳng. Nhấn để chuyển sang STRUCTURED."
                Case BomDisplayMode.Structured
                    _displayModeButton.Text = "STRUCTURED"
                    _displayModeButton.ToolTipText = "Cây Assembly cha-con + Local Qty. Nhấn để chuyển sang HYBRID."
                Case Else
                    _displayModeButton.Text = "HYBRID BOM"
                    _displayModeButton.ToolTipText = "Cây Assembly + Local/Total Quantity. Nhấn để chuyển sang PARTS ONLY."
            End Select
        End If
        LoadRows()
    End Sub

    Private Function IsPathCollapsed(ByVal groupPath As String) As Boolean
        If String.IsNullOrWhiteSpace(groupPath) Then Return False
        For Each collapsedPath As String In _collapsedGroups
            If String.Equals(groupPath, collapsedPath, StringComparison.OrdinalIgnoreCase) Then Return True
            If groupPath.StartsWith(collapsedPath & "\", StringComparison.OrdinalIgnoreCase) Then Return True
        Next
        Return False
    End Function

    Private Sub ToggleCurrentGroupClicked(ByVal sender As Object, ByVal e As EventArgs)
        If Not _groupedView OrElse Grid.CurrentRow Is Nothing Then Exit Sub
        Dim groupName As String = GetRowGroupName(Grid.CurrentRow)
        If groupName.Length = 0 Then Exit Sub
        ToggleGroup(groupName)
    End Sub

    Private Sub ToggleGroup(ByVal groupName As String)
        If Not _groupedView OrElse String.IsNullOrWhiteSpace(groupName) Then Exit Sub
        If _collapsedGroups.Contains(groupName) Then
            _collapsedGroups.Remove(groupName)
        Else
            _collapsedGroups.Add(groupName)
        End If
        For Each row As DataGridViewRow In Grid.Rows
            If IsAssemblyHeaderRow(row) AndAlso String.Equals(GetRowGroupName(row), groupName, StringComparison.OrdinalIgnoreCase) Then
                row.Cells("ITEM").Value = If(_collapsedGroups.Contains(groupName), "▸", "▾")
            End If
        Next
        ApplySearchFilter()
    End Sub

    Private Sub CollapseAllGroupsClicked(ByVal sender As Object, ByVal e As EventArgs)
        If Not _groupedView Then Exit Sub
        For Each row As DataGridViewRow In Grid.Rows
            If IsAssemblyHeaderRow(row) Then _collapsedGroups.Add(GetRowGroupName(row))
        Next
        For Each row As DataGridViewRow In Grid.Rows
            If IsAssemblyHeaderRow(row) Then row.Cells("ITEM").Value = "▸"
        Next
        ApplySearchFilter()
    End Sub

    Private Sub ExpandAllGroupsClicked(ByVal sender As Object, ByVal e As EventArgs)
        _collapsedGroups.Clear()
        For Each row As DataGridViewRow In Grid.Rows
            If IsAssemblyHeaderRow(row) Then row.Cells("ITEM").Value = "▾"
        Next
        ApplySearchFilter()
    End Sub

    Private Sub ToggleMarkClicked(ByVal sender As Object, ByVal e As EventArgs)
        Dim rowsToProcess As New List(Of DataGridViewRow)()
        If Grid.SelectedRows.Count > 0 Then
            For Each row As DataGridViewRow In Grid.SelectedRows
                rowsToProcess.Add(row)
            Next
        ElseIf Grid.CurrentRow IsNot Nothing Then
            rowsToProcess.Add(Grid.CurrentRow)
        End If

        For Each row As DataGridViewRow In rowsToProcess
            If IsAssemblyHeaderRow(row) Then
                Dim groupName As String = GetRowGroupName(row)
                Dim shouldMark As Boolean = False
                For Each child As DataGridViewRow In Grid.Rows
                    Dim childItem As PartBomItem = TryCast(child.Tag, PartBomItem)
                    If childItem IsNot Nothing AndAlso String.Equals(GetRowGroupName(child), groupName, StringComparison.OrdinalIgnoreCase) AndAlso Not _markedPartKeys.Contains(childItem.DocumentKey) Then
                        shouldMark = True
                        Exit For
                    End If
                Next
                For Each child As DataGridViewRow In Grid.Rows
                    Dim childItem As PartBomItem = TryCast(child.Tag, PartBomItem)
                    If childItem IsNot Nothing AndAlso String.Equals(GetRowGroupName(child), groupName, StringComparison.OrdinalIgnoreCase) Then
                        If shouldMark Then _markedPartKeys.Add(childItem.DocumentKey) Else _markedPartKeys.Remove(childItem.DocumentKey)
                        ApplyMarkStyle(child, childItem)
                    End If
                Next
            Else
                Dim item As PartBomItem = TryCast(row.Tag, PartBomItem)
                If item IsNot Nothing Then
                    If _markedPartKeys.Contains(item.DocumentKey) Then _markedPartKeys.Remove(item.DocumentKey) Else _markedPartKeys.Add(item.DocumentKey)
                    For Each relatedRow As DataGridViewRow In Grid.Rows
                        Dim relatedItem As PartBomItem = TryCast(relatedRow.Tag, PartBomItem)
                        If relatedItem IsNot Nothing AndAlso String.Equals(relatedItem.DocumentKey, item.DocumentKey, StringComparison.OrdinalIgnoreCase) Then ApplyMarkStyle(relatedRow, relatedItem)
                    Next
                End If
            End If
        Next
        Grid.Invalidate()
    End Sub

    Private Sub ApplyMarkStyle(ByVal row As DataGridViewRow, ByVal item As PartBomItem)
        If row Is Nothing OrElse item Is Nothing Then Exit Sub
        row.DefaultCellStyle.BackColor = If(_markedPartKeys.Contains(item.DocumentKey), Color.FromArgb(255, 245, 170), Color.White)
    End Sub

    Private Sub ClearAllMarksClicked(ByVal sender As Object, ByVal e As EventArgs)
        _markedPartKeys.Clear()
        For Each row As DataGridViewRow In Grid.Rows
            Dim item As PartBomItem = TryCast(row.Tag, PartBomItem)
            If item IsNot Nothing Then ApplyMarkStyle(row, item)
        Next
        Grid.Invalidate()
    End Sub

    Private Sub ClearTableClicked(ByVal sender As Object, ByVal e As EventArgs)
        If Grid.Rows.Count = 0 Then Exit Sub
        Dim result As DialogResult = MessageBox.Show("Xóa dữ liệu đang hiển thị khỏi bảng?" & vbCrLf & "Thao tác này không xóa hoặc sửa file Inventor.", "CLEAR TABLE", MessageBoxButtons.YesNo, MessageBoxIcon.Question)
        If result <> DialogResult.Yes Then Exit Sub
        Grid.Rows.Clear()
        SearchBox.Clear()
        UpdateStatusBar(0, 0, 0)
    End Sub


'####################################################################
' SUBSECTION 15.13 - COLUMN LAYOUT / SAVE WORKSPACE
'####################################################################

    Private Sub ManageColumnsClicked(ByVal sender As Object, ByVal e As EventArgs)
        Dim form As New BomColumnManagerForm(Grid)
        form.ShowDialog(Me)
        ApplySearchFilter()
    End Sub

    Private Sub SaveLayoutClicked(ByVal sender As Object, ByVal e As EventArgs)
        SaveLayout(True)
    End Sub

    Private Sub SaveLayout(ByVal showMessage As Boolean)
        Try
            Dim lines As New List(Of String)()
            For Each column As DataGridViewColumn In Grid.Columns
                lines.Add(column.Name & "|" & column.DisplayIndex.ToString() & "|" & column.Width.ToString() & "|" & column.Visible.ToString())
            Next
            System.IO.File.WriteAllLines(_layoutFile, lines.ToArray(), System.Text.Encoding.UTF8)
            If showMessage Then MessageBox.Show("Đã lưu bố cục cột.", "BOM TOOL PRO", MessageBoxButtons.OK, MessageBoxIcon.Information)
        Catch ex As Exception
            MessageBox.Show("Không lưu được bố cục." & vbCrLf & ex.Message, "BOM TOOL PRO", MessageBoxButtons.OK, MessageBoxIcon.Error)
        End Try
    End Sub

    Private Sub LoadLayoutClicked(ByVal sender As Object, ByVal e As EventArgs)
        TryLoadLayout(True)
    End Sub

    Private Sub TryLoadLayout(ByVal showMessage As Boolean)
        Try
            If Not System.IO.File.Exists(_layoutFile) Then
                If showMessage Then MessageBox.Show("Chưa có bố cục đã lưu.", "BOM TOOL PRO", MessageBoxButtons.OK, MessageBoxIcon.Information)
                Exit Sub
            End If
            Dim records As New List(Of String())()
            For Each line As String In System.IO.File.ReadAllLines(_layoutFile, System.Text.Encoding.UTF8)
                Dim parts() As String = line.Split("|"c)
                If parts.Length >= 4 Then records.Add(parts)
            Next
            records.Sort(Function(a As String(), b As String()) Convert.ToInt32(a(1)).CompareTo(Convert.ToInt32(b(1))))
            Dim displayIndex As Integer = 0
            For Each parts() As String In records
                If Grid.Columns.Contains(parts(0)) Then
                    Dim col As DataGridViewColumn = Grid.Columns(parts(0))
                    col.Width = Math.Max(45, Convert.ToInt32(parts(2)))
                    col.Visible = Convert.ToBoolean(parts(3))
                    col.DisplayIndex = Math.Min(displayIndex, Grid.Columns.Count - 1)
                    displayIndex += 1
                End If
            Next
            If showMessage Then MessageBox.Show("Đã nạp bố cục cột.", "BOM TOOL PRO", MessageBoxButtons.OK, MessageBoxIcon.Information)
        Catch ex As Exception
            If showMessage Then MessageBox.Show("Không nạp được bố cục." & vbCrLf & ex.Message, "BOM TOOL PRO", MessageBoxButtons.OK, MessageBoxIcon.Error)
        End Try
    End Sub

    Private Sub ResetLayoutClicked(ByVal sender As Object, ByVal e As EventArgs)
        Dim displayIndex As Integer = 0
        For Each column As DataGridViewColumn In Grid.Columns
            column.Visible = True
            column.DisplayIndex = displayIndex
            displayIndex += 1
        Next
        Grid.AutoResizeColumns(System.Windows.Forms.DataGridViewAutoSizeColumnsMode.DisplayedCells)
    End Sub


'####################################################################
' SUBSECTION 15.14 - OPEN PART / DRAWING / DRAWING INDEX
'####################################################################

    Private Sub OpenPartClicked(ByVal sender As Object, ByVal e As EventArgs)
        If Grid.CurrentRow IsNot Nothing AndAlso IsAssemblyHeaderRow(Grid.CurrentRow) Then
            OpenAssemblySelected()
        Else
            OpenPart(GetCurrentItem())
        End If
    End Sub

    Private Sub OpenPart(ByVal item As PartBomItem)
        If item Is Nothing OrElse String.IsNullOrWhiteSpace(item.FilePath) Then Exit Sub
        Try
            _inventor.Documents.Open(item.FilePath, True)
        Catch ex As Exception
            MessageBox.Show("Không mở được Part." & vbCrLf & ex.Message, "BOM TOOL PRO", MessageBoxButtons.OK, MessageBoxIcon.Error)
        End Try
    End Sub

    Private Sub OpenDrawingClicked(ByVal sender As Object, ByVal e As EventArgs)
        If Grid.CurrentRow IsNot Nothing AndAlso IsAssemblyHeaderRow(Grid.CurrentRow) Then
            Dim assemblyPath As String = GetCurrentAssemblyPath()
            If assemblyPath.Length = 0 Then Exit Sub
            Dim drawingPath As String = FindDrawingPath(assemblyPath)
            If drawingPath.Length = 0 Then
                MessageBox.Show("Không tìm thấy Drawing của Assembly đang chọn.", "BOM TOOL PRO", MessageBoxButtons.OK, MessageBoxIcon.Information)
                Exit Sub
            End If
            Try : _inventor.Documents.Open(drawingPath, True) : Catch ex As Exception : MessageBox.Show("Không mở được Drawing Assembly." & vbCrLf & ex.Message, "BOM TOOL PRO", MessageBoxButtons.OK, MessageBoxIcon.Error) : End Try
        Else
            OpenDrawing(GetCurrentItem())
        End If
    End Sub

    'Mở Drawing của Part được truyền vào.
    'Được dùng chung cho nút trên thanh công cụ, menu chuột phải
    'và thao tác nhấn chuột trái một lần tại cột DRAWING.
    Private Sub OpenDrawing(ByVal item As PartBomItem)
        If item Is Nothing Then Exit Sub

        Dim drawingPath As String = FindDrawingPath(item.FilePath)

        If String.IsNullOrWhiteSpace(drawingPath) Then
            MessageBox.Show( _
                "Không tìm thấy bản vẽ IDW hoặc DWG của Part:" & vbCrLf & _
                item.FileName & vbCrLf & vbCrLf & _
                "Bạn có thể dùng chức năng CHỈ ĐỊNH DRAWING để chọn file thủ công.", _
                "BOM TOOL PRO", _
                MessageBoxButtons.OK, _
                MessageBoxIcon.Information)
            Exit Sub
        End If

        Try
            _inventor.Documents.Open(drawingPath, True)
        Catch ex As Exception
            MessageBox.Show( _
                "Không mở được Drawing." & vbCrLf & ex.Message, _
                "BOM TOOL PRO", _
                MessageBoxButtons.OK, _
                MessageBoxIcon.Error)
        End Try
    End Sub

    Private Function FindDrawingPath(ByVal partPath As String) As String
        BomPerformanceCounters.DrawingSearch += 1
        If String.IsNullOrWhiteSpace(partPath) Then Return ""

        '1. Đường dẫn do người dùng chỉ định trước đó
        If _manualDrawingMap.ContainsKey(partPath) Then
            Dim mappedPath As String = _manualDrawingMap(partPath)
            If System.IO.File.Exists(mappedPath) Then Return mappedPath
        End If

        Dim folder As String = IOPath.GetDirectoryName(partPath)
        Dim baseName As String = IOPath.GetFileNameWithoutExtension(partPath)

        '2. Drawing nằm cùng thư mục với Part
        Dim idw As String = IOPath.Combine(folder, baseName & ".idw")
        If System.IO.File.Exists(idw) Then Return idw
        Dim dwg As String = IOPath.Combine(folder, baseName & ".dwg")
        If System.IO.File.Exists(dwg) Then Return dwg

        '3. Tra trong chỉ mục Drawing đã quét một lần khi mở BOM
        If _drawingIndex.ContainsKey(baseName) Then
            Dim indexedPath As String = _drawingIndex(baseName)
            If System.IO.File.Exists(indexedPath) Then Return indexedPath
        End If

        Return ""
    End Function

    '================================================================
    ' TẠO CHỈ MỤC DRAWING MỘT LẦN, KHÔNG TÌM LẠI CHO TỪNG DÒNG
    '================================================================
    Private Sub BuildDrawingIndex()
        Dim drawingWatch As Stopwatch = Stopwatch.StartNew()
        _drawingIndex.Clear()

        Dim folders As New HashSet(Of String)(StringComparer.OrdinalIgnoreCase)
        AddFolderIfValid(folders, IOPath.GetDirectoryName(_assemblyPath))

        For Each item As PartBomItem In _allItems
            If item Is Nothing OrElse String.IsNullOrWhiteSpace(item.FilePath) Then Continue For
            Dim partFolder As String = IOPath.GetDirectoryName(item.FilePath)
            AddFolderIfValid(folders, partFolder)

            Dim parentFolder As String = IOPath.GetDirectoryName(partFolder)
            If Not String.IsNullOrWhiteSpace(parentFolder) Then
                AddKnownDrawingFolders(folders, parentFolder)
                Dim grandParent As String = IOPath.GetDirectoryName(parentFolder)
                If Not String.IsNullOrWhiteSpace(grandParent) Then AddKnownDrawingFolders(folders, grandParent)
            End If
        Next

        Dim assemblyFolder As String = IOPath.GetDirectoryName(_assemblyPath)
        If Not String.IsNullOrWhiteSpace(assemblyFolder) Then
            AddKnownDrawingFolders(folders, assemblyFolder)
            Dim assemblyParent As String = IOPath.GetDirectoryName(assemblyFolder)
            If Not String.IsNullOrWhiteSpace(assemblyParent) Then AddKnownDrawingFolders(folders, assemblyParent)
        End If

        For Each folder As String In folders
            IndexDrawingFilesInFolder(folder)
        Next
        drawingWatch.Stop()
        BomPerformanceCounters.DrawingIndexMs += drawingWatch.ElapsedMilliseconds
    End Sub

    Private Sub AddFolderIfValid(ByVal folders As HashSet(Of String), ByVal folder As String)
        If String.IsNullOrWhiteSpace(folder) Then Exit Sub
        Try
            If System.IO.Directory.Exists(folder) Then folders.Add(folder)
        Catch
        End Try
    End Sub

    Private Sub AddKnownDrawingFolders(ByVal folders As HashSet(Of String), ByVal rootFolder As String)
        If String.IsNullOrWhiteSpace(rootFolder) OrElse Not System.IO.Directory.Exists(rootFolder) Then Exit Sub

        Dim knownNames() As String = {
            "DRAWING", "DRAWINGS", "IDW", "DWG", "2D",
            "BAN VE", "BẢN VẼ", "BANVE", "DRAWING FILE", "DRAWING_FILES"}

        For Each folderName As String In knownNames
            AddFolderIfValid(folders, IOPath.Combine(rootFolder, folderName))
        Next

        'Nhận cả thư mục có tên gần giống Drawing ở cấp con trực tiếp
        Try
            For Each childFolder As String In System.IO.Directory.GetDirectories(rootFolder)
                Dim childName As String = IOPath.GetFileName(childFolder).ToUpperInvariant()
                If childName.Contains("DRAW") OrElse childName.Contains("IDW") OrElse _
                   childName.Contains("DWG") OrElse childName.Contains("BAN VE") OrElse _
                   childName.Contains("BẢN VẼ") Then
                    AddFolderIfValid(folders, childFolder)
                End If
            Next
        Catch
        End Try
    End Sub

    Private Sub IndexDrawingFilesInFolder(ByVal folder As String)
        If String.IsNullOrWhiteSpace(folder) Then Exit Sub
        Try
            For Each filePath As String In System.IO.Directory.GetFiles(folder, "*.idw", System.IO.SearchOption.TopDirectoryOnly)
                AddDrawingToIndex(filePath)
            Next
            For Each filePath As String In System.IO.Directory.GetFiles(folder, "*.dwg", System.IO.SearchOption.TopDirectoryOnly)
                AddDrawingToIndex(filePath)
            Next
        Catch
            'Không có quyền đọc thư mục hoặc đường dẫn mạng tạm mất
        End Try
    End Sub

    Private Sub AddDrawingToIndex(ByVal drawingPath As String)
        If String.IsNullOrWhiteSpace(drawingPath) Then Exit Sub
        Dim baseName As String = IOPath.GetFileNameWithoutExtension(drawingPath)
        If String.IsNullOrWhiteSpace(baseName) Then Exit Sub

        'Ưu tiên IDW nếu cùng tên tồn tại cả IDW và DWG
        If Not _drawingIndex.ContainsKey(baseName) Then
            _drawingIndex.Add(baseName, drawingPath)
        ElseIf IOPath.GetExtension(drawingPath).Equals(".idw", StringComparison.OrdinalIgnoreCase) Then
            _drawingIndex(baseName) = drawingPath
        End If
    End Sub

    '================================================================
    ' CHỈ ĐỊNH DRAWING THỦ CÔNG KHI DRAWING KHÔNG CÙNG TÊN/THƯ MỤC
    '================================================================
    Private Sub LocateDrawingClicked(ByVal sender As Object, ByVal e As EventArgs)
        Dim item As PartBomItem = GetCurrentItem()
        If item Is Nothing Then Exit Sub

        Dim dialog As New OpenFileDialog()
        dialog.Title = "Chọn Drawing cho Part: " & item.PartNumber
        dialog.Filter = "Inventor Drawing (*.idw;*.dwg)|*.idw;*.dwg|Inventor IDW (*.idw)|*.idw|Drawing DWG (*.dwg)|*.dwg"
        dialog.CheckFileExists = True
        dialog.Multiselect = False

        Try
            Dim currentDrawing As String = FindDrawingPath(item.FilePath)
            If Not String.IsNullOrWhiteSpace(currentDrawing) Then
                dialog.InitialDirectory = IOPath.GetDirectoryName(currentDrawing)
                dialog.FileName = IOPath.GetFileName(currentDrawing)
            ElseIf Not String.IsNullOrWhiteSpace(item.FilePath) Then
                dialog.InitialDirectory = IOPath.GetDirectoryName(item.FilePath)
            End If
        Catch
        End Try

        If dialog.ShowDialog() <> DialogResult.OK Then Exit Sub

        _manualDrawingMap(item.FilePath) = dialog.FileName
        AddDrawingToIndex(dialog.FileName)
        SaveManualDrawingMap()
        RefreshDrawingStatusForItem(item)
    End Sub

    Private Sub RefreshDrawingStatusForItem(ByVal item As PartBomItem)
        For Each row As DataGridViewRow In Grid.Rows
            If row.Tag Is item Then
                Dim status As String = GetDrawingStatus(item.FilePath)
                row.Cells("DRAWING_STATUS").Value = status
                If status = "MISSING" Then
                    row.Cells("DRAWING_STATUS").Style.BackColor = Color.White
                    row.Cells("DRAWING_STATUS").Style.ForeColor = Color.FromArgb(165, 70, 70)
                Else
                    row.Cells("DRAWING_STATUS").Style.BackColor = Color.White
                    row.Cells("DRAWING_STATUS").Style.ForeColor = Color.FromArgb(45, 105, 78)
                End If
            End If
        Next
        'Tính lại số dòng hiển thị, tổng QTY và số Drawing còn thiếu
        ApplySearchFilter()
    End Sub

    Private Sub LoadManualDrawingMap()
        _manualDrawingMap.Clear()
        If String.IsNullOrWhiteSpace(_drawingMapFile) OrElse Not System.IO.File.Exists(_drawingMapFile) Then Exit Sub
        Try
            For Each line As String In System.IO.File.ReadAllLines(_drawingMapFile)
                Dim separatorIndex As Integer = line.IndexOf("|"c)
                If separatorIndex <= 0 Then Continue For
                Dim partPath As String = line.Substring(0, separatorIndex)
                Dim drawingPath As String = line.Substring(separatorIndex + 1)
                If partPath.Length > 0 AndAlso drawingPath.Length > 0 Then
                    _manualDrawingMap(partPath) = drawingPath
                End If
            Next
        Catch
        End Try
    End Sub

    Private Sub SaveManualDrawingMap()
        If String.IsNullOrWhiteSpace(_drawingMapFile) Then Exit Sub
        Try
            Dim lines As New List(Of String)()
            For Each pair As KeyValuePair(Of String, String) In _manualDrawingMap
                lines.Add(pair.Key & "|" & pair.Value)
            Next
            System.IO.File.WriteAllLines(_drawingMapFile, lines.ToArray())
        Catch
        End Try
    End Sub

    Private Sub BuildExcelFormulaBar(ByVal root As System.Windows.Forms.TableLayoutPanel)
        Dim panel As New Panel()
        panel.Dock = DockStyle.Fill
        panel.BackColor = Color.FromArgb(247, 249, 250)
        panel.Padding = New System.Windows.Forms.Padding(4, 3, 4, 3)

        ExcelNameBox = New TextBox()
        ExcelNameBox.Left = 4
        ExcelNameBox.Top = 4
        ExcelNameBox.Width = 86
        ExcelNameBox.Height = 25
        ExcelNameBox.TextAlign = HorizontalAlignment.Center
        ExcelNameBox.Text = "A1"
        AddHandler ExcelNameBox.KeyDown, AddressOf ExcelNameBoxKeyDown
        panel.Controls.Add(ExcelNameBox)

        Dim fxLabel As New Label()
        fxLabel.Text = "fx"
        fxLabel.Font = New Font("Segoe UI Semibold", 10.0F, FontStyle.Italic)
        fxLabel.TextAlign = ContentAlignment.MiddleCenter
        fxLabel.Left = 94

'####################################################################
' SUBSECTION 15.15 - EXCEL-LIKE FORMULA BAR / CELL ADDRESS / SELECTION
'####################################################################

        fxLabel.Top = 4
        fxLabel.Width = 34
        fxLabel.Height = 25
        panel.Controls.Add(fxLabel)

        ExcelFormulaApply = New Button()
        ExcelFormulaApply.Text = "✓"
        ExcelFormulaApply.Left = 130
        ExcelFormulaApply.Top = 3
        ExcelFormulaApply.Width = 34
        ExcelFormulaApply.Height = 27
        AddHandler ExcelFormulaApply.Click, AddressOf ExcelFormulaApplyClicked
        panel.Controls.Add(ExcelFormulaApply)

        ExcelFormulaBox = New TextBox()
        ExcelFormulaBox.Left = 168
        ExcelFormulaBox.Top = 4
        ExcelFormulaBox.Height = 25
        ExcelFormulaBox.Anchor = AnchorStyles.Left Or AnchorStyles.Top Or AnchorStyles.Right
        ExcelFormulaBox.Width = Math.Max(200, panel.ClientSize.Width - 172)
        AddHandler panel.Resize, Sub(sender As Object, e As EventArgs)
            ExcelFormulaBox.Width = Math.Max(200, panel.ClientSize.Width - 172)
        End Sub
        AddHandler ExcelFormulaBox.KeyDown, AddressOf ExcelFormulaBoxKeyDown
        panel.Controls.Add(ExcelFormulaBox)
        root.Controls.Add(panel, 0, 2)
    End Sub

    Private Function ColumnIndexToExcelName(ByVal columnIndex As Integer) As String
        Dim value As Integer = columnIndex + 1
        Dim result As String = ""
        While value > 0
            value -= 1
            result = ChrW(65 + (value Mod 26)) & result
            value \= 26
        End While
        Return result
    End Function

    Private Function ExcelColumnNameToIndex(ByVal text As String) As Integer
        Dim value As Integer = 0
        For Each ch As Char In text.ToUpperInvariant()
            If ch < "A"c OrElse ch > "Z"c Then Return -1
            value = value * 26 + (AscW(ch) - AscW("A"c) + 1)
        Next
        Return value - 1
    End Function

    Private Sub ExcelNameBoxKeyDown(ByVal sender As Object, ByVal e As System.Windows.Forms.KeyEventArgs)
        If e.KeyCode <> System.Windows.Forms.Keys.Enter Then Exit Sub
        Dim address As String = ExcelNameBox.Text.Trim().ToUpperInvariant()
        Dim letters As String = ""
        Dim digits As String = ""
        For Each ch As Char In address
            If Char.IsLetter(ch) AndAlso digits.Length = 0 Then
                letters &= ch
            ElseIf Char.IsDigit(ch) Then
                digits &= ch
            End If
        Next
        Dim colIndex As Integer = ExcelColumnNameToIndex(letters)
        Dim rowNumber As Integer = 0
        If Not Integer.TryParse(digits, rowNumber) Then rowNumber = 0
        Dim rowIndex As Integer = rowNumber - 1
        If colIndex >= 0 AndAlso colIndex < Grid.Columns.Count AndAlso rowIndex >= 0 AndAlso rowIndex < Grid.Rows.Count Then
            Grid.CurrentCell = Grid.Rows(rowIndex).Cells(colIndex)
            Grid.FirstDisplayedScrollingRowIndex = Math.Max(0, rowIndex)
            If Grid.Columns(colIndex).Visible Then Grid.FirstDisplayedScrollingColumnIndex = colIndex
        End If
        e.Handled = True
        e.SuppressKeyPress = True
    End Sub

    Private Sub ExcelFormulaBoxKeyDown(ByVal sender As Object, ByVal e As System.Windows.Forms.KeyEventArgs)
        If e.KeyCode = System.Windows.Forms.Keys.Enter Then
            ExcelFormulaApplyClicked(sender, EventArgs.Empty)
            e.Handled = True
            e.SuppressKeyPress = True
        ElseIf e.KeyCode = System.Windows.Forms.Keys.Escape Then
            UpdateExcelFormulaBar()
            Grid.Focus()
            e.Handled = True
            e.SuppressKeyPress = True
        End If
    End Sub

    Private Sub ExcelFormulaApplyClicked(ByVal sender As Object, ByVal e As EventArgs)
        If Grid.CurrentCell Is Nothing Then Exit Sub
        ApplyGridPropertyValue(Grid.CurrentCell.RowIndex, Grid.CurrentCell.ColumnIndex, ExcelFormulaBox.Text)
        Grid.Focus()
        UpdateExcelFormulaBar()
    End Sub

    Private Sub UpdateExcelFormulaBar()
        If ExcelNameBox Is Nothing OrElse ExcelFormulaBox Is Nothing Then Exit Sub
        If Grid Is Nothing OrElse Grid.CurrentCell Is Nothing Then
            ExcelNameBox.Text = ""
            ExcelFormulaBox.Text = ""
            Exit Sub
        End If
        ExcelNameBox.Text = ColumnIndexToExcelName(Grid.CurrentCell.ColumnIndex) & (Grid.CurrentCell.RowIndex + 1).ToString()
        If Not ExcelFormulaBox.Focused Then ExcelFormulaBox.Text = Convert.ToString(Grid.CurrentCell.Value)
    End Sub

    Private Sub GridCellValueChangedForFormula(ByVal sender As Object, ByVal e As DataGridViewCellEventArgs)
        If Grid.CurrentCell IsNot Nothing AndAlso e.RowIndex = Grid.CurrentCell.RowIndex AndAlso e.ColumnIndex = Grid.CurrentCell.ColumnIndex Then UpdateExcelFormulaBar()
    End Sub

    Private Sub GridRowPostPaint(ByVal sender As Object, ByVal e As System.Windows.Forms.DataGridViewRowPostPaintEventArgs)
        Dim text As String = (e.RowIndex + 1).ToString()
        Dim bounds As New Rectangle(e.RowBounds.Left, e.RowBounds.Top, Grid.RowHeadersWidth - 5, e.RowBounds.Height)
        System.Windows.Forms.TextRenderer.DrawText(e.Graphics, text, Grid.Font, bounds, Color.FromArgb(55, 75, 85), TextFormatFlags.Right Or TextFormatFlags.VerticalCenter)
    End Sub


'####################################################################
' SUBSECTION 15.16 - ROW/COLUMN HEADER SELECTION / SORT / FREEZE
'####################################################################

    Private Sub GridColumnHeaderMouseClick(ByVal sender As Object, ByVal e As DataGridViewCellMouseEventArgs)
        If e.ColumnIndex < 0 OrElse e.Button <> MouseButtons.Left Then Exit Sub
        If e.ColumnIndex >= Grid.Columns.Count Then Exit Sub

        Dim clickedColumn As DataGridViewColumn = Grid.Columns(e.ColumnIndex)
        If clickedColumn Is Nothing OrElse clickedColumn.SortMode = DataGridViewColumnSortMode.NotSortable Then Exit Sub

        'Excel-like: click header = sort. Ctrl/Shift vẫn dùng để chọn cả cột/range,
        'nhưng sort luôn được xử lý bởi engine riêng để không phá Assembly Group.
        ApplyColumnSort(clickedColumn.Name, Nothing)

        Dim controlDown As Boolean = (Control.ModifierKeys And Keys.Control) = Keys.Control
        Dim shiftDown As Boolean = (Control.ModifierKeys And Keys.Shift) = Keys.Shift
        Dim startIndex As Integer = e.ColumnIndex
        Dim endIndex As Integer = e.ColumnIndex
        If shiftDown AndAlso _lastSelectedColumn >= 0 Then
            startIndex = Math.Min(_lastSelectedColumn, e.ColumnIndex)
            endIndex = Math.Max(_lastSelectedColumn, e.ColumnIndex)
        End If
        SelectColumnRange(startIndex, endIndex, controlDown)
        _lastSelectedColumn = e.ColumnIndex
        Dim target As DataGridViewCell = FirstVisibleCellInColumn(e.ColumnIndex)
        If target IsNot Nothing Then Grid.CurrentCell = target
        UpdateExcelSelectionStatus()
    End Sub

    Private Sub SelectColumnRange(ByVal startIndex As Integer, ByVal endIndex As Integer, ByVal preserveSelection As Boolean)
        If Not preserveSelection Then Grid.ClearSelection()
        For c As Integer = Math.Max(0, startIndex) To Math.Min(Grid.Columns.Count - 1, endIndex)
            If Grid.Columns(c).Visible Then
                For Each row As DataGridViewRow In Grid.Rows
                    If row.Visible Then row.Cells(c).Selected = True
                Next
            End If
        Next
    End Sub

    Private Function FirstVisibleCellInColumn(ByVal columnIndex As Integer) As DataGridViewCell
        If columnIndex < 0 OrElse columnIndex >= Grid.Columns.Count Then Return Nothing
        For Each row As DataGridViewRow In Grid.Rows
            If row.Visible Then Return row.Cells(columnIndex)
        Next
        Return Nothing
    End Function

    Private Function FirstVisibleCellInRow(ByVal rowIndex As Integer) As DataGridViewCell
        If rowIndex < 0 OrElse rowIndex >= Grid.Rows.Count Then Return Nothing
        For Each col As DataGridViewColumn In Grid.Columns
            If col.Visible Then Return Grid.Rows(rowIndex).Cells(col.Index)
        Next
        Return Nothing
    End Function

    Private Sub GridRowHeaderMouseClick(ByVal sender As Object, ByVal e As DataGridViewCellMouseEventArgs)
        If e.RowIndex < 0 OrElse e.Button <> MouseButtons.Left Then Exit Sub
        If Grid.SelectionMode <> DataGridViewSelectionMode.FullRowSelect Then
            Grid.SelectionMode = DataGridViewSelectionMode.FullRowSelect
            Grid.MultiSelect = True
        End If
        Dim controlDown As Boolean = (Control.ModifierKeys And Keys.Control) = Keys.Control
        Dim shiftDown As Boolean = (Control.ModifierKeys And Keys.Shift) = Keys.Shift
        If Not controlDown AndAlso Not shiftDown Then Grid.ClearSelection()
        Dim startIndex As Integer = e.RowIndex
        Dim endIndex As Integer = e.RowIndex
        If shiftDown AndAlso _lastSelectedRow >= 0 Then
            startIndex = Math.Min(_lastSelectedRow, e.RowIndex)
            endIndex = Math.Max(_lastSelectedRow, e.RowIndex)
        End If
        For r As Integer = startIndex To endIndex
            If Grid.Rows(r).Visible Then Grid.Rows(r).Selected = True
        Next
        _lastSelectedRow = e.RowIndex
        Grid.CurrentCell = Grid.Rows(e.RowIndex).Cells(0)
        UpdateExcelSelectionStatus()
    End Sub

    Private Sub UpdateExcelSelectionStatus()
        If StatusSelection Is Nothing OrElse Grid Is Nothing Then Exit Sub
        Dim count As Integer = Grid.SelectedCells.Count
        If count = 0 Then
            StatusSelection.Text = "Chọn ô để xem thống kê"
            Exit Sub
        End If
        Dim numericCount As Integer = 0
        Dim sum As Double = 0
        Dim minValue As Double = Double.MaxValue
        Dim maxValue As Double = Double.MinValue
        For Each cell As DataGridViewCell In Grid.SelectedCells
            Dim number As Double
            Dim text As String = Convert.ToString(cell.Value).Trim().Replace(",", ".")
            If Double.TryParse(text, System.Globalization.NumberStyles.Any, System.Globalization.CultureInfo.InvariantCulture, number) Then
                numericCount += 1
                sum += number
                minValue = Math.Min(minValue, number)
                maxValue = Math.Max(maxValue, number)
            End If
        Next
        If numericCount > 0 Then
            Dim address As String = If(Grid.CurrentCell Is Nothing, "", ColumnIndexToExcelName(Grid.CurrentCell.ColumnIndex) & (Grid.CurrentCell.RowIndex + 1).ToString() & "   ")
            StatusSelection.Text = address & "Count: " & count.ToString() & "   Sum: " & sum.ToString("0.###") & "   Average: " & (sum / numericCount).ToString("0.###") & "   Min: " & minValue.ToString("0.###") & "   Max: " & maxValue.ToString("0.###")
        Else
            Dim address As String = If(Grid.CurrentCell Is Nothing, "", ColumnIndexToExcelName(Grid.CurrentCell.ColumnIndex) & (Grid.CurrentCell.RowIndex + 1).ToString() & "   ")
            StatusSelection.Text = address & "Count: " & count.ToString()
        End If
    End Sub

    Private Sub SelectCurrentColumnClicked(ByVal sender As Object, ByVal e As EventArgs)
        Dim index As Integer = If(_contextColumnIndex >= 0, _contextColumnIndex, If(Grid.CurrentCell Is Nothing, -1, Grid.CurrentCell.ColumnIndex))
        If index < 0 Then Exit Sub
        SelectColumnRange(index, index, False)
        Dim target As DataGridViewCell = FirstVisibleCellInColumn(index)
        If target IsNot Nothing Then Grid.CurrentCell = target
        UpdateExcelSelectionStatus()
    End Sub

    Private Sub SelectCurrentRowClicked(ByVal sender As Object, ByVal e As EventArgs)
        Dim index As Integer = If(_contextRowIndex >= 0, _contextRowIndex, If(Grid.CurrentCell Is Nothing, -1, Grid.CurrentCell.RowIndex))
        If index < 0 OrElse index >= Grid.Rows.Count Then Exit Sub
        If Grid.SelectionMode <> DataGridViewSelectionMode.FullRowSelect Then
            Grid.SelectionMode = DataGridViewSelectionMode.FullRowSelect
            Grid.MultiSelect = True
        End If
        Grid.ClearSelection()
        Grid.Rows(index).Selected = True
        Dim target As DataGridViewCell = FirstVisibleCellInRow(index)
        If target IsNot Nothing Then Grid.CurrentCell = target
        UpdateExcelSelectionStatus()
    End Sub

    Private Sub SortAscendingClicked(ByVal sender As Object, ByVal e As EventArgs)
        SortCurrentColumn(System.ComponentModel.ListSortDirection.Ascending)
    End Sub

    Private Sub SortDescendingClicked(ByVal sender As Object, ByVal e As EventArgs)
        SortCurrentColumn(System.ComponentModel.ListSortDirection.Descending)
    End Sub

    '================================================================
    ' SMART STOCK NUMBER SORT
    ' Integrated from the useful core idea of sort-part-lists-by-stock-number.vb.
    ' Unlike the original drawing-only rule, this works directly on BOM Tool's
    ' cached data model, remains group-safe, and does not require the Stock Number
    ' column to be visible.
    '================================================================
    Private Sub SortByStockNumberClicked(ByVal sender As Object, ByVal e As EventArgs)
        _activeSortColumn = "__STOCK_NUMBER__"
        _activeSortDirection = System.ComponentModel.ListSortDirection.Ascending
        LoadRows()
        Try
            If StatusSelection IsNot Nothing Then
                StatusSelection.Text = "Đã sắp xếp BOM theo Stock Number (A → Z)"
            End If
        Catch
        End Try
    End Sub

    Private Sub SortCurrentColumn(ByVal direction As System.ComponentModel.ListSortDirection)
        Dim index As Integer = If(_contextColumnIndex >= 0, _contextColumnIndex, If(Grid.CurrentCell Is Nothing, -1, Grid.CurrentCell.ColumnIndex))
        If index < 0 OrElse index >= Grid.Columns.Count Then Exit Sub
        ApplyColumnSort(Grid.Columns(index).Name, direction)
    End Sub

    '================================================================
    ' V13.2 - GROUP SAFE SORT ENGINE
    '================================================================
    Private Sub ApplyColumnSort(ByVal columnName As String, ByVal forcedDirection As Nullable(Of System.ComponentModel.ListSortDirection))
        If String.IsNullOrWhiteSpace(columnName) OrElse Not Grid.Columns.Contains(columnName) Then Exit Sub

        If forcedDirection.HasValue Then
            _activeSortDirection = forcedDirection.Value
        ElseIf String.Equals(_activeSortColumn, columnName, StringComparison.OrdinalIgnoreCase) Then
            If _activeSortDirection = System.ComponentModel.ListSortDirection.Ascending Then
                _activeSortDirection = System.ComponentModel.ListSortDirection.Descending
            Else
                _activeSortDirection = System.ComponentModel.ListSortDirection.Ascending
            End If
        Else
            _activeSortDirection = System.ComponentModel.ListSortDirection.Ascending
        End If

        _activeSortColumn = columnName

        'Re-render từ Data Model. Như vậy Assembly header không bao giờ là phần tử sort.
        LoadRows()
    End Sub

    Private Sub SortItemsForCurrentView(ByVal items As List(Of PartBomItem), ByVal groupName As String)
        If items Is Nothing OrElse items.Count <= 1 Then Exit Sub

        If String.IsNullOrWhiteSpace(_activeSortColumn) Then
            items.Sort(AddressOf CompareBomItems)
            Exit Sub
        End If

        Dim sortKeys As New Dictionary(Of String, Object)(StringComparer.OrdinalIgnoreCase)
        For Each item As PartBomItem In items
            If item Is Nothing Then Continue For
            sortKeys(GetSortCacheKey(item, groupName)) = GetItemSortValue(item, _activeSortColumn, groupName)
        Next

        items.Sort(Function(a As PartBomItem, b As PartBomItem) As Integer
            If a Is Nothing AndAlso b Is Nothing Then Return 0
            If a Is Nothing Then Return 1
            If b Is Nothing Then Return -1

            Dim keyA As String = GetSortCacheKey(a, groupName)
            Dim keyB As String = GetSortCacheKey(b, groupName)
            Dim valueA As Object = If(sortKeys.ContainsKey(keyA), sortKeys(keyA), Nothing)
            Dim valueB As Object = If(sortKeys.ContainsKey(keyB), sortKeys(keyB), Nothing)
            Dim result As Integer = CompareSortValues(valueA, valueB)

            'Tie-breaker ổn định để cùng giá trị không nhảy lung tung giữa các lần click.
            If result = 0 Then result = CompareBomItems(a, b)
            If _activeSortDirection = System.ComponentModel.ListSortDirection.Descending Then result = -result
            Return result
        End Function)
    End Sub

    Private Function GetSortCacheKey(ByVal item As PartBomItem, ByVal groupName As String) As String
        If item Is Nothing Then Return Guid.NewGuid().ToString()
        Dim key As String = If(String.IsNullOrWhiteSpace(item.DocumentKey), item.FilePath, item.DocumentKey)
        Return If(key, "") & "|" & If(groupName, "")
    End Function

    Private Function GetItemSortValue(ByVal item As PartBomItem, ByVal columnName As String, ByVal groupName As String) As Object
        If item Is Nothing Then Return Nothing
        Dim name As String = If(columnName, "").Trim().ToUpperInvariant()

        Select Case name
            Case "ITEM"
                'ITEM là số hiển thị được sinh lại sau sort, không dùng mũi tên header làm số 0.
                'Dùng thứ tự BOM gốc làm khóa ổn định.
                Return item.PartNumber & "|" & item.FileName
            Case "QTY"
                If _groupedView AndAlso Not String.IsNullOrWhiteSpace(groupName) Then
                    Return item.GetQuantityForParent(groupName)
                End If
                Return item.Quantity
            Case "__STOCK_NUMBER__"
                Return item.StockNumber
            Case "FILE_NAME"
                Return item.FileName
            Case "FILE_PATH"
                Return item.FilePath
            Case "PARENT_ASSEMBLY"
                If _groupedView AndAlso Not String.IsNullOrWhiteSpace(groupName) Then Return groupName
                Return item.GetParentAssemblyText()
            Case "DRAWING_STATUS"
                Return GetDrawingStatus(item.FilePath)
            Case "DATA_STATUS"
                Return GetDataStatus(item)
        End Select

        'Dynamic Feature columns
        For Each featureKey As String In _enabledFeatures
            If _featureRegistry.ContainsKey(featureKey) Then
                Dim featureDef As BomFeatureDefinition = _featureRegistry(featureKey)
                If featureDef IsNot Nothing AndAlso String.Equals(featureDef.ColumnName, columnName, StringComparison.OrdinalIgnoreCase) Then
                    Return GetFeatureDisplayValue(item, featureKey)
                End If
            End If
        Next

        'Selected iProperty columns
        For Each p As PropertyColumnInfo In _selectedProperties
            If p IsNot Nothing AndAlso String.Equals(p.Key, columnName, StringComparison.OrdinalIgnoreCase) Then
                Return BomUnitManager.GetPropertyDisplayValue(item, p)
            End If
        Next

        Return ""
    End Function

    Private Function CompareSortValues(ByVal leftValue As Object, ByVal rightValue As Object) As Integer
        Dim leftEmpty As Boolean = leftValue Is Nothing OrElse String.IsNullOrWhiteSpace(Convert.ToString(leftValue))
        Dim rightEmpty As Boolean = rightValue Is Nothing OrElse String.IsNullOrWhiteSpace(Convert.ToString(rightValue))

        'Ô trống luôn xuống cuối, bất kể Asc/Desc.
        If leftEmpty AndAlso rightEmpty Then Return 0
        If leftEmpty Then Return 1
        If rightEmpty Then Return -1

        Dim leftNumber As Double
        Dim rightNumber As Double
        Dim leftText As String = Convert.ToString(leftValue).Trim().Replace(",", ".")
        Dim rightText As String = Convert.ToString(rightValue).Trim().Replace(",", ".")
        Dim leftIsNumber As Boolean = Double.TryParse(leftText, System.Globalization.NumberStyles.Any, System.Globalization.CultureInfo.InvariantCulture, leftNumber)
        Dim rightIsNumber As Boolean = Double.TryParse(rightText, System.Globalization.NumberStyles.Any, System.Globalization.CultureInfo.InvariantCulture, rightNumber)
        If leftIsNumber AndAlso rightIsNumber Then Return leftNumber.CompareTo(rightNumber)

        Dim leftDate As DateTime
        Dim rightDate As DateTime
        If DateTime.TryParse(Convert.ToString(leftValue), leftDate) AndAlso DateTime.TryParse(Convert.ToString(rightValue), rightDate) Then
            Return leftDate.CompareTo(rightDate)
        End If

        Return StringComparer.OrdinalIgnoreCase.Compare(Convert.ToString(leftValue), Convert.ToString(rightValue))
    End Function

    Private Sub UpdateSortGlyph()
        If Grid Is Nothing Then Exit Sub
        For Each col As DataGridViewColumn In Grid.Columns
            If col.HeaderCell Is Nothing Then Continue For
            col.HeaderCell.SortGlyphDirection = System.Windows.Forms.SortOrder.None
        Next
        If String.IsNullOrWhiteSpace(_activeSortColumn) OrElse Not Grid.Columns.Contains(_activeSortColumn) Then Exit Sub
        If _activeSortDirection = System.ComponentModel.ListSortDirection.Ascending Then
            Grid.Columns(_activeSortColumn).HeaderCell.SortGlyphDirection = System.Windows.Forms.SortOrder.Ascending
        Else
            Grid.Columns(_activeSortColumn).HeaderCell.SortGlyphDirection = System.Windows.Forms.SortOrder.Descending
        End If
    End Sub


'####################################################################
' SUBSECTION 15.17 - CUT / FILL / AUTOFIT / HIDE / SHOW
'####################################################################

    Private Sub CutSelectedCellsClicked(ByVal sender As Object, ByVal e As EventArgs)
        CopySelectedCellsClicked(sender, e)
        _cutMode = True
        ClearSelectedCellsClicked(sender, e)
    End Sub

    Private Sub FillRightClicked(ByVal sender As Object, ByVal e As EventArgs)
        If Grid.CurrentCell Is Nothing Then Exit Sub
        Dim sourceRow As Integer = Grid.CurrentCell.RowIndex
        Dim sourceValue As String = Convert.ToString(Grid.CurrentCell.Value)
        Dim targetColumns As New SortedSet(Of Integer)()
        For Each cell As DataGridViewCell In Grid.SelectedCells
            If cell.RowIndex = sourceRow Then targetColumns.Add(cell.ColumnIndex)
        Next
        Dim changed As Integer = 0
        For Each columnIndex As Integer In targetColumns
            If columnIndex <> Grid.CurrentCell.ColumnIndex AndAlso ApplyGridPropertyValue(sourceRow, columnIndex, sourceValue) Then changed += 1
        Next
        MessageBox.Show("Đã Fill Right " & changed.ToString() & " ô.", "BOM TOOL PRO", MessageBoxButtons.OK, MessageBoxIcon.Information)
    End Sub

    Private Sub AutoFitSelectedColumnsClicked(ByVal sender As Object, ByVal e As EventArgs)
        Dim indexes As New HashSet(Of Integer)()
        For Each cell As DataGridViewCell In Grid.SelectedCells
            indexes.Add(cell.ColumnIndex)
        Next
        If indexes.Count = 0 AndAlso Grid.CurrentCell IsNot Nothing Then indexes.Add(Grid.CurrentCell.ColumnIndex)
        For Each index As Integer In indexes
            Try
                Grid.AutoResizeColumn(index, DataGridViewAutoSizeColumnMode.DisplayedCells)
            Catch
            End Try
        Next
    End Sub

    Private Sub HideSelectedColumnsClicked(ByVal sender As Object, ByVal e As EventArgs)
        Dim indexes As New List(Of Integer)()
        For Each cell As DataGridViewCell In Grid.SelectedCells
            If Not indexes.Contains(cell.ColumnIndex) Then indexes.Add(cell.ColumnIndex)
        Next
        If indexes.Count = 0 AndAlso Grid.CurrentCell IsNot Nothing Then indexes.Add(Grid.CurrentCell.ColumnIndex)
        If Grid.Columns.Count - indexes.Count < 1 Then Exit Sub
        For Each index As Integer In indexes
            Grid.Columns(index).Visible = False
        Next
    End Sub

    Private Sub ShowAllColumnsClicked(ByVal sender As Object, ByVal e As EventArgs)
        For Each column As DataGridViewColumn In Grid.Columns
            column.Visible = True
        Next
    End Sub

    Private Sub FreezeToCurrentColumnClicked(ByVal sender As Object, ByVal e As EventArgs)
        If Grid.CurrentCell Is Nothing Then Exit Sub
        Dim stopIndex As Integer = Grid.CurrentCell.ColumnIndex
        For Each column As DataGridViewColumn In Grid.Columns
            column.Frozen = column.Index <= stopIndex
        Next
    End Sub

    Private Sub UnfreezeColumnsClicked(ByVal sender As Object, ByVal e As EventArgs)
        For Each column As DataGridViewColumn In Grid.Columns
            column.Frozen = False
        Next
    End Sub

    Private Sub ToggleCellSelectionModeClicked(ByVal sender As Object, ByVal e As EventArgs)
        'Toggle thật sự giữa FullRowSelect và Excel CellSelect.
        If Grid.SelectionMode = DataGridViewSelectionMode.FullRowSelect AndAlso _forceFullRowSelection Then
            _forceFullRowSelection = False
            Grid.SelectionMode = DataGridViewSelectionMode.CellSelect
            Grid.MultiSelect = True
            StatusLoadTime.Text = "Chế độ Excel: chọn ô/vùng | click số hàng = chọn cả hàng"
        Else
            _forceFullRowSelection = True
            Grid.SelectionMode = DataGridViewSelectionMode.FullRowSelect
            Grid.MultiSelect = True
            StatusLoadTime.Text = "Chế độ chọn hàng: Ctrl/Shift chọn nhiều hàng | bấm lại để về Excel"
        End If
    End Sub


'####################################################################
' SUBSECTION 15.18 - COPY / PASTE / CLEAR / KEYBOARD SHORTCUTS
'####################################################################

    Private Sub CopyCurrentCellClicked(ByVal sender As Object, ByVal e As EventArgs)
        If Grid.CurrentCell Is Nothing Then Exit Sub
        Try
            Clipboard.SetText(Convert.ToString(Grid.CurrentCell.FormattedValue))
        Catch ex As Exception
            MessageBox.Show("Không copy được ô hiện tại." & vbCrLf & ex.Message, "BOM TOOL PRO", MessageBoxButtons.OK, MessageBoxIcon.Error)
        End Try
    End Sub

    Private Sub CopySelectedCellsClicked(ByVal sender As Object, ByVal e As EventArgs)
        If Grid.SelectedCells.Count = 0 Then
            CopyCurrentCellClicked(sender, e)
            Exit Sub
        End If
        Try
            Dim minRow As Integer = Integer.MaxValue
            Dim maxRow As Integer = -1
            Dim minCol As Integer = Integer.MaxValue
            Dim maxCol As Integer = -1
            For Each cell As System.Windows.Forms.DataGridViewCell In Grid.SelectedCells
                If cell.OwningRow.Visible AndAlso cell.OwningColumn.Visible Then
                    minRow = Math.Min(minRow, cell.RowIndex)
                    maxRow = Math.Max(maxRow, cell.RowIndex)
                    minCol = Math.Min(minCol, cell.ColumnIndex)
                    maxCol = Math.Max(maxCol, cell.ColumnIndex)
                End If
            Next
            If maxRow < 0 OrElse maxCol < 0 Then Exit Sub

            Dim selectedKeys As New HashSet(Of String)()
            For Each cell As System.Windows.Forms.DataGridViewCell In Grid.SelectedCells
                selectedKeys.Add(cell.RowIndex.ToString() & "|" & cell.ColumnIndex.ToString())
            Next

            Dim sb As New StringBuilder()
            For r As Integer = minRow To maxRow
                If Not Grid.Rows(r).Visible Then Continue For
                Dim firstValue As Boolean = True
                For c As Integer = minCol To maxCol
                    If Not Grid.Columns(c).Visible Then Continue For
                    If Not firstValue Then sb.Append(vbTab)
                    firstValue = False
                    If selectedKeys.Contains(r.ToString() & "|" & c.ToString()) Then
                        Dim textValue As String = Convert.ToString(Grid.Rows(r).Cells(c).FormattedValue)
                        textValue = textValue.Replace(vbCr, " ").Replace(vbLf, " ").Replace(vbTab, " ")
                        sb.Append(textValue)
                    End If
                Next
                sb.AppendLine()
            Next
            Clipboard.SetText(sb.ToString().TrimEnd(ControlChars.Cr, ControlChars.Lf))
        Catch ex As Exception
            MessageBox.Show("Không copy được vùng dữ liệu." & vbCrLf & ex.Message, "BOM TOOL PRO", MessageBoxButtons.OK, MessageBoxIcon.Error)
        End Try
    End Sub

    Private Function ApplyGridPropertyValue(ByVal rowIndex As Integer, ByVal columnIndex As Integer, ByVal newValue As String) As Boolean
        If rowIndex < 0 OrElse columnIndex < 0 OrElse rowIndex >= Grid.Rows.Count OrElse columnIndex >= Grid.Columns.Count Then Return False
        Dim row As DataGridViewRow = Grid.Rows(rowIndex)
        Dim item As PartBomItem = TryCast(row.Tag, PartBomItem)
        Dim col As DataGridViewColumn = Grid.Columns(columnIndex)
        Dim propertyInfo As PropertyColumnInfo = TryCast(col.Tag, PropertyColumnInfo)
        If item Is Nothing OrElse propertyInfo Is Nothing OrElse col.ReadOnly Then Return False
        Dim oldValue As String = Convert.ToString(row.Cells(columnIndex).Value)
        If String.Equals(oldValue, newValue, StringComparison.Ordinal) Then Return True
        _suppressCellWrite = True
        row.Cells(columnIndex).Value = newValue
        _suppressCellWrite = False
        StagePropertyChange(item, propertyInfo, oldValue, newValue, row, columnIndex)
        Return True
    End Function

    Private Sub PasteCellsClicked(ByVal sender As Object, ByVal e As EventArgs)
        If Not EnsureWriteAllowed("Paste Property") Then Exit Sub
        If Grid.CurrentCell Is Nothing OrElse Not Clipboard.ContainsText() Then Exit Sub
        Dim clipboardText As String = Clipboard.GetText()
        If String.IsNullOrEmpty(clipboardText) Then Exit Sub
        Dim rowsText() As String = clipboardText.Replace(vbCrLf, vbLf).Replace(vbCr, vbLf).Split(New String() {vbLf}, StringSplitOptions.None)
        Dim startRow As Integer = Grid.CurrentCell.RowIndex
        Dim startCol As Integer = Grid.CurrentCell.ColumnIndex
        Dim changed As Integer = 0
        Dim skipped As Integer = 0

        Dim effectiveRows As New List(Of String)()
        For i As Integer = 0 To rowsText.Length - 1
            If i = rowsText.Length - 1 AndAlso rowsText(i).Length = 0 Then Continue For
            effectiveRows.Add(rowsText(i))
        Next

        'Excel behavior: clipboard chỉ có 1 ô + đang chọn nhiều ô => điền cùng giá trị vào toàn vùng chọn.
        If effectiveRows.Count = 1 AndAlso effectiveRows(0).IndexOf(ControlChars.Tab) < 0 AndAlso Grid.SelectedCells.Count > 1 Then
            Dim oneValue As String = effectiveRows(0)
            Dim selected As New List(Of DataGridViewCell)()
            For Each cell As DataGridViewCell In Grid.SelectedCells : selected.Add(cell) : Next
            selected.Sort(Function(a As DataGridViewCell, b As DataGridViewCell)
                              Dim cr As Integer = a.RowIndex.CompareTo(b.RowIndex)
                              If cr <> 0 Then Return cr
                              Return a.ColumnIndex.CompareTo(b.ColumnIndex)
                          End Function)
            For Each cell As DataGridViewCell In selected
                If ApplyGridPropertyValue(cell.RowIndex, cell.ColumnIndex, oneValue) Then changed += 1 Else skipped += 1
            Next
        Else
            For r As Integer = 0 To effectiveRows.Count - 1
                Dim values() As String = effectiveRows(r).Split(ControlChars.Tab)
                For c As Integer = 0 To values.Length - 1
                    Dim targetRow As Integer = startRow + r
                    Dim targetCol As Integer = startCol + c
                    If targetRow >= Grid.Rows.Count OrElse targetCol >= Grid.Columns.Count Then
                        skipped += 1
                    ElseIf ApplyGridPropertyValue(targetRow, targetCol, values(c)) Then
                        changed += 1
                    Else
                        skipped += 1
                    End If
                Next
            Next
        End If
        If _cutMode AndAlso changed > 0 Then _cutMode = False
        StatusLoadTime.Text = "Paste: " & changed.ToString() & " ô" & If(skipped > 0, " | bỏ qua " & skipped.ToString(), "")
    End Sub

    Private Sub FillDownClicked(ByVal sender As Object, ByVal e As EventArgs)
        If Not EnsureWriteAllowed("Fill Down") Then Exit Sub
        If Grid.CurrentCell Is Nothing Then Exit Sub
        Dim sourceColumn As Integer = Grid.CurrentCell.ColumnIndex
        Dim sourceValue As String = Convert.ToString(Grid.CurrentCell.Value)
        Dim targetRows As New SortedSet(Of Integer)()
        For Each cell As System.Windows.Forms.DataGridViewCell In Grid.SelectedCells
            If cell.ColumnIndex = sourceColumn Then targetRows.Add(cell.RowIndex)
        Next
        If targetRows.Count = 0 Then
            For Each row As DataGridViewRow In Grid.SelectedRows
                targetRows.Add(row.Index)
            Next
        End If
        Dim changed As Integer = 0
        For Each rowIndex As Integer In targetRows
            If rowIndex <> Grid.CurrentCell.RowIndex AndAlso ApplyGridPropertyValue(rowIndex, sourceColumn, sourceValue) Then changed += 1
        Next
        StatusLoadTime.Text = "Fill Down: " & changed.ToString() & " ô"
    End Sub

    Private Sub GridFillHandleMouseMove(ByVal sender As Object, ByVal e As MouseEventArgs)
        If Not _fillDragging Then
            Dim overHandle As Boolean = False
            If Grid.CurrentCell IsNot Nothing Then
                Dim col As DataGridViewColumn = Grid.Columns(Grid.CurrentCell.ColumnIndex)
                Dim item As PartBomItem = TryCast(Grid.Rows(Grid.CurrentCell.RowIndex).Tag, PartBomItem)
                Dim pi As PropertyColumnInfo = TryCast(col.Tag, PropertyColumnInfo)
                If item IsNot Nothing AndAlso pi IsNot Nothing AndAlso Not col.ReadOnly Then
                    Dim cellRect As Rectangle = Grid.GetCellDisplayRectangle(Grid.CurrentCell.ColumnIndex, Grid.CurrentCell.RowIndex, False)
                    Dim handleRect As New Rectangle(cellRect.Right - FillHandleSize - 2, cellRect.Bottom - FillHandleSize - 2, FillHandleSize + 4, FillHandleSize + 4)
                    overHandle = handleRect.Contains(New Point(e.X, e.Y))
                End If
            End If
            Grid.Cursor = If(overHandle, System.Windows.Forms.Cursors.Cross, System.Windows.Forms.Cursors.Default)
            Exit Sub
        End If
        If _fillSourceRow < 0 OrElse _fillSourceColumn < 0 Then Exit Sub

        'Auto-scroll nhẹ khi kéo sát mép trên/dưới.
        Try
            If e.Y >= Grid.ClientSize.Height - 18 AndAlso Grid.FirstDisplayedScrollingRowIndex >= 0 Then
                Dim nextRow As Integer = Math.Min(Grid.Rows.Count - 1, Grid.FirstDisplayedScrollingRowIndex + 1)
                If nextRow >= 0 AndAlso Grid.Rows(nextRow).Visible Then Grid.FirstDisplayedScrollingRowIndex = nextRow
            ElseIf e.Y <= Grid.ColumnHeadersHeight + 18 AndAlso Grid.FirstDisplayedScrollingRowIndex > 0 Then
                Dim previousRow As Integer = Math.Max(0, Grid.FirstDisplayedScrollingRowIndex - 1)
                If Grid.Rows(previousRow).Visible Then Grid.FirstDisplayedScrollingRowIndex = previousRow
            End If
        Catch
        End Try

        Dim hit As System.Windows.Forms.DataGridView.HitTestInfo = Grid.HitTest(e.X, e.Y)
        If hit.RowIndex < 0 Then Exit Sub
        _fillTargetRow = hit.RowIndex

        Grid.ClearSelection()
        Dim firstRow As Integer = Math.Min(_fillSourceRow, _fillTargetRow)
        Dim lastRow As Integer = Math.Max(_fillSourceRow, _fillTargetRow)
        For r As Integer = firstRow To lastRow
            If r >= 0 AndAlso r < Grid.Rows.Count AndAlso Grid.Rows(r).Visible Then
                Grid.Rows(r).Cells(_fillSourceColumn).Selected = True
            End If
        Next
        Grid.Invalidate()
    End Sub

    Private Sub GridFillHandleMouseUp(ByVal sender As Object, ByVal e As MouseEventArgs)
        If Not _fillDragging Then Exit Sub
        Dim sourceRow As Integer = _fillSourceRow
        Dim sourceColumn As Integer = _fillSourceColumn
        Dim targetRow As Integer = _fillTargetRow
        _fillDragging = False
        _fillSourceRow = -1
        _fillSourceColumn = -1
        _fillTargetRow = -1
        Grid.Capture = False
        Grid.Cursor = System.Windows.Forms.Cursors.Default

        If sourceRow < 0 OrElse sourceColumn < 0 OrElse targetRow < 0 OrElse targetRow = sourceRow Then
            Grid.Invalidate()
            Exit Sub
        End If
        If Not EnsureWriteAllowed("Fill Handle") Then Exit Sub

        Dim sourceValue As String = Convert.ToString(Grid.Rows(sourceRow).Cells(sourceColumn).Value)
        Dim firstRow As Integer = Math.Min(sourceRow, targetRow)
        Dim lastRow As Integer = Math.Max(sourceRow, targetRow)
        Dim changed As Integer = 0
        Dim skipped As Integer = 0
        For r As Integer = firstRow To lastRow
            If r = sourceRow OrElse Not Grid.Rows(r).Visible Then Continue For
            If ApplyGridPropertyValue(r, sourceColumn, sourceValue) Then changed += 1 Else skipped += 1
        Next
        StatusLoadTime.Text = "Auto Fill: " & changed.ToString() & " ô" & If(skipped > 0, " | bỏ qua " & skipped.ToString(), "")
        Grid.Invalidate()
    End Sub

    Private Sub ClearSelectedCellsClicked(ByVal sender As Object, ByVal e As EventArgs)
        If Not EnsureWriteAllowed("Clear Property") Then Exit Sub
        Dim cells As New List(Of System.Windows.Forms.DataGridViewCell)()
        For Each cell As System.Windows.Forms.DataGridViewCell In Grid.SelectedCells
            cells.Add(cell)
        Next
        If cells.Count = 0 AndAlso Grid.CurrentCell IsNot Nothing Then cells.Add(Grid.CurrentCell)
        Dim changed As Integer = 0
        For Each cell As System.Windows.Forms.DataGridViewCell In cells
            If ApplyGridPropertyValue(cell.RowIndex, cell.ColumnIndex, "") Then changed += 1
        Next
        If changed > 0 Then MessageBox.Show("Đã xóa nội dung " & changed.ToString() & " ô iProperty.", "BOM TOOL PRO", MessageBoxButtons.OK, MessageBoxIcon.Information)
    End Sub

    Private Sub SelectAllCellsClicked(ByVal sender As Object, ByVal e As EventArgs)
        Grid.SelectAll()
    End Sub

    Private Sub GridKeyDown(ByVal sender As Object, ByVal e As System.Windows.Forms.KeyEventArgs)
        'SMART REFRESH V20: F5 = Incremental | Ctrl+F5 = all selected iProperty | Shift+F5 = Full Reload.
        If e.KeyCode = Keys.F5 Then
            RefreshClicked(sender, EventArgs.Empty)
            e.Handled = True
            e.SuppressKeyPress = True
            Exit Sub
        End If

        'Interaction shortcuts ưu tiên khi đang ở chế độ chọn dòng.
        If e.KeyCode = Keys.Enter Then
            If e.Control Then
                OpenDrawingClicked(sender, EventArgs.Empty)
            Else
                OpenPartClicked(sender, EventArgs.Empty)
            End If
            e.Handled = True
            e.SuppressKeyPress = True
        ElseIf e.KeyCode = Keys.Space AndAlso Not e.Control AndAlso Not e.Shift Then
            HighlightCurrent(False, False)
            e.Handled = True
            e.SuppressKeyPress = True
        ElseIf e.KeyCode = Keys.Delete AndAlso Grid.SelectionMode = DataGridViewSelectionMode.FullRowSelect Then
            HideSelectedRowsInteractive()
            e.Handled = True
            e.SuppressKeyPress = True
        ElseIf e.Control AndAlso e.KeyCode = Keys.C Then
            CopySelectedCellsClicked(sender, EventArgs.Empty)
            e.Handled = True
            e.SuppressKeyPress = True
        ElseIf e.Control AndAlso e.KeyCode = Keys.X Then
            CutSelectedCellsClicked(sender, EventArgs.Empty)
            e.Handled = True
            e.SuppressKeyPress = True
        ElseIf e.Control AndAlso e.KeyCode = Keys.V Then
            PasteCellsClicked(sender, EventArgs.Empty)
            e.Handled = True
            e.SuppressKeyPress = True
        ElseIf e.Control AndAlso e.KeyCode = Keys.A Then
            Grid.SelectAll()
            e.Handled = True
        ElseIf e.Control AndAlso e.KeyCode = Keys.D Then
            FillDownClicked(sender, EventArgs.Empty)
            e.Handled = True
        ElseIf e.Control AndAlso e.KeyCode = Keys.R Then
            FillRightClicked(sender, EventArgs.Empty)
            e.Handled = True
        ElseIf e.Control AndAlso e.KeyCode = Keys.F Then
            SearchBox.Focus()
            SearchBox.SelectAll()
            e.Handled = True
        ElseIf e.Control AndAlso e.KeyCode = Keys.Space Then
            SelectCurrentColumnClicked(sender, EventArgs.Empty)
            e.Handled = True
        ElseIf e.Shift AndAlso e.KeyCode = Keys.Space Then
            SelectCurrentRowClicked(sender, EventArgs.Empty)
            e.Handled = True
        ElseIf e.Control AndAlso e.KeyCode = Keys.Home Then
            MoveToExcelEdge(False)
            e.Handled = True
        ElseIf e.Control AndAlso e.KeyCode = Keys.End Then
            MoveToExcelEdge(True)
            e.Handled = True
        ElseIf e.Control AndAlso Not e.Shift AndAlso e.KeyCode = Keys.D0 Then
            HideSelectedColumnsClicked(sender, EventArgs.Empty)
            e.Handled = True
        ElseIf e.Control AndAlso e.Shift AndAlso e.KeyCode = Keys.D0 Then
            ShowAllColumnsClicked(sender, EventArgs.Empty)
            e.Handled = True
        ElseIf e.KeyCode = Keys.Delete Then
            ClearSelectedCellsClicked(sender, EventArgs.Empty)
            e.Handled = True
        ElseIf e.KeyCode = Keys.F2 AndAlso Grid.CurrentCell IsNot Nothing Then
            Grid.BeginEdit(True)
            e.Handled = True
        End If
    End Sub

    Private Sub HideSelectedRowsInteractive()
        Dim rowsToHide As New List(Of DataGridViewRow)()
        For Each row As DataGridViewRow In Grid.SelectedRows
            If row IsNot Nothing AndAlso row.Visible AndAlso Not IsAssemblyHeaderRow(row) Then rowsToHide.Add(row)
        Next
        If rowsToHide.Count = 0 AndAlso Grid.CurrentRow IsNot Nothing AndAlso Not IsAssemblyHeaderRow(Grid.CurrentRow) Then
            rowsToHide.Add(Grid.CurrentRow)
        End If
        For Each row As DataGridViewRow In rowsToHide
            Try
                row.Visible = False
            Catch
            End Try
        Next
        StatusLoadTime.Text = "Đã ẩn " & rowsToHide.Count.ToString() & " dòng (Refresh để hiện lại)"
    End Sub

    Private Sub MoveToExcelEdge(ByVal moveToEnd As Boolean)
        If Grid.Rows.Count = 0 OrElse Grid.Columns.Count = 0 Then Exit Sub
        Dim rowIndex As Integer = If(moveToEnd, Grid.Rows.Count - 1, 0)
        Dim columnIndex As Integer = If(moveToEnd, Grid.Columns.Count - 1, 0)
        While rowIndex >= 0 AndAlso rowIndex < Grid.Rows.Count AndAlso Not Grid.Rows(rowIndex).Visible
            rowIndex += If(moveToEnd, -1, 1)
        End While
        While columnIndex >= 0 AndAlso columnIndex < Grid.Columns.Count AndAlso Not Grid.Columns(columnIndex).Visible
            columnIndex += If(moveToEnd, -1, 1)
        End While
        If rowIndex >= 0 AndAlso rowIndex < Grid.Rows.Count AndAlso columnIndex >= 0 AndAlso columnIndex < Grid.Columns.Count Then
            Grid.CurrentCell = Grid.Rows(rowIndex).Cells(columnIndex)
            Grid.FirstDisplayedScrollingRowIndex = rowIndex
            Grid.FirstDisplayedScrollingColumnIndex = columnIndex
        End If
    End Sub


'####################################################################
' SUBSECTION 15.19 - FILE ACTIONS / WHERE USED
'####################################################################

    Private Sub OpenFolderClicked(ByVal sender As Object, ByVal e As EventArgs)
        Dim item As PartBomItem = GetCurrentItem()
        If item Is Nothing OrElse String.IsNullOrWhiteSpace(item.FilePath) Then Exit Sub
        Try
            System.Diagnostics.Process.Start("explorer.exe", "/select,""" & item.FilePath & """")
        Catch ex As Exception
            MessageBox.Show("Không mở được thư mục." & vbCrLf & ex.Message, "BOM TOOL PRO", MessageBoxButtons.OK, MessageBoxIcon.Error)
        End Try
    End Sub

    Private Sub CopyPartNumberClicked(ByVal sender As Object, ByVal e As EventArgs)
        Dim item As PartBomItem = GetCurrentItem()
        If item IsNot Nothing Then Clipboard.SetText(If(item.PartNumber, ""))
    End Sub

    Private Sub CopyPathClicked(ByVal sender As Object, ByVal e As EventArgs)
        Dim item As PartBomItem = GetCurrentItem()
        If item IsNot Nothing Then Clipboard.SetText(If(item.FilePath, ""))
    End Sub

    Private Sub WhereUsedClicked(ByVal sender As Object, ByVal e As EventArgs)
        ShowDependencyImpact(False)
    End Sub

    Private Sub AppendWhereUsedNodeText(ByVal node As BomWhereUsedNode, ByVal sb As System.Text.StringBuilder, ByVal depth As Integer)
        If node Is Nothing Then Exit Sub
        If depth > 0 Then
            sb.Append(New String(" "c, Math.Min(40, (depth - 1) * 3)))
            sb.Append("└─ ")
            sb.Append(node.Name)
            sb.Append("   Local Qty: ")
            sb.Append(node.LocalQty.ToString())
            sb.Append("   Occ: ")
            sb.Append(node.OccurrenceCount.ToString())
            sb.AppendLine()
        End If
        node.Children.Sort(Function(a As BomWhereUsedNode, b As BomWhereUsedNode) StringComparer.OrdinalIgnoreCase.Compare(a.Name, b.Name))
        For Each child As BomWhereUsedNode In node.Children
            AppendWhereUsedNodeText(child, sb, depth + 1)
        Next
    End Sub

    Private Sub ImpactAnalysisClicked(ByVal sender As Object, ByVal e As EventArgs)
        ShowDependencyImpact(True)
    End Sub

    Private Sub FinalRegressionClicked(ByVal sender As Object, ByVal e As EventArgs)
        BomSafeExecution.Run("FINAL REGRESSION CHECK",
            Sub()
                Dim checks As List(Of BomRegressionCheck) =
                    BomRegressionEngine.Run(_allItems, _structureRoot, _activeSnapshot)

                Dim passed As Integer = 0
                Dim failed As Integer = 0
                Dim sb As New System.Text.StringBuilder()
                sb.AppendLine(BomReleaseInfo.Version & " - " & BomReleaseInfo.ReleaseName)
                sb.AppendLine(BomReleaseInfo.Architecture)
                sb.AppendLine(New String("-"c, 72))

                For Each c As BomRegressionCheck In checks
                    If c.Passed Then passed += 1 Else failed += 1
                    sb.Append(If(c.Passed, "[PASS] ", "[FAIL] "))
                    sb.Append(c.Name)
                    sb.Append("  -  ")
                    sb.AppendLine(c.Detail)
                Next

                sb.AppendLine(New String("-"c, 72))
                sb.AppendLine("PASS: " & passed.ToString() & "   FAIL: " & failed.ToString())
                sb.AppendLine("RUNTIME ERRORS: " & BomProductionDiagnostics.ErrorCount.ToString())
                sb.AppendLine("RECOVERIES: " & BomProductionDiagnostics.RecoveryCount.ToString())
                sb.AppendLine()
                If failed = 0 Then
                    sb.AppendLine("RELEASE STATUS: READY FOR PRODUCTION")
                Else
                    sb.AppendLine("RELEASE STATUS: REVIEW FAILED CHECKS BEFORE PRODUCTION")
                End If

                ShowProjectIntelligenceText("V23 FINAL REGRESSION", sb.ToString())
            End Sub)
    End Sub

    Private Sub HealthCheckClicked(ByVal sender As Object, ByVal e As EventArgs)
        BomSafeExecution.Run("HEALTH CHECK",
            Sub()
                Dim result As BomIntegrityResult = BomIntegrityEngine.Check(_allItems, _structureRoot)
                Dim sb As New System.Text.StringBuilder()
                sb.AppendLine(If(result.IsHealthy(), "STATUS: HEALTHY", "STATUS: ERROR"))
                sb.AppendLine("ITEMS: " & If(_allItems Is Nothing, 0, _allItems.Count).ToString())
                sb.AppendLine("ERRORS: " & result.Errors.Count.ToString())
                sb.AppendLine("WARNINGS: " & result.Warnings.Count.ToString())
                sb.AppendLine("RECOVERIES: " & BomProductionDiagnostics.RecoveryCount.ToString())
                sb.AppendLine("RUNTIME ERRORS: " & BomProductionDiagnostics.ErrorCount.ToString())
                If result.Errors.Count > 0 Then
                    sb.AppendLine().AppendLine("ERROR DETAIL:")
                    For Each s As String In result.Errors
                        sb.AppendLine(" • " & s)
                    Next
                End If
                If result.Warnings.Count > 0 Then
                    sb.AppendLine().AppendLine("WARNING DETAIL:")
                    For Each s As String In result.Warnings
                        sb.AppendLine(" • " & s)
                    Next
                End If
                ShowProjectIntelligenceText("PRODUCTION HEALTH CHECK", sb.ToString())
            End Sub)
    End Sub

    Private Sub RecoverUiClicked(ByVal sender As Object, ByVal e As EventArgs)
        BomSafeExecution.Run("RECOVER UI",
            Sub()
                _suppressCellWrite = True
                Try
                    Grid.EndEdit()
                Catch
                End Try
                Try
                    Grid.ClearSelection()
                Catch
                End Try
                _quickFilterMode = "ALL"
                _collapsedGroups.Clear()
                BomDependencyCache.Clear()
                LoadRows()
                BomProductionDiagnostics.RecoveryCount += 1
            End Sub)
        _suppressCellWrite = False
    End Sub

    Private Sub CommandPaletteClicked(ByVal sender As Object, ByVal e As EventArgs)
        Dim commands As New List(Of BomCommandItem)()
        AddPaletteCommand(commands, "Refresh", "BOM", "Refresh dữ liệu BOM.", Sub() RefreshClicked(Nothing, EventArgs.Empty))
        AddPaletteCommand(commands, "Highlight", "VIEW", "Highlight Part đang chọn.", Sub() HighlightCurrent(False, False))
        AddPaletteCommand(commands, "Where Used 2.0", "INTELLIGENCE", "Dependency Tree.", Sub() WhereUsedClicked(Nothing, EventArgs.Empty))
        AddPaletteCommand(commands, "Impact Analysis", "INTELLIGENCE", "Phân tích ảnh hưởng.", Sub() ImpactAnalysisClicked(Nothing, EventArgs.Empty))
        AddPaletteCommand(commands, "Snapshot", "CHANGE", "Chụp trạng thái BOM.", Sub() CaptureSnapshotClicked(Nothing, EventArgs.Empty))
        AddPaletteCommand(commands, "Compare Snapshot", "CHANGE", "So sánh với Snapshot.", Sub() CompareSnapshotClicked(Nothing, EventArgs.Empty))
        AddPaletteCommand(commands, "Manufacturing Summary", "MANUFACTURING", "Dashboard sản xuất/mua hàng.", Sub() ManufacturingSummaryClicked(Nothing, EventArgs.Empty))
        AddPaletteCommand(commands, "Report Center", "REPORT", "BOM Report.", Sub() ReportCenterClicked(Nothing, EventArgs.Empty))
        AddPaletteCommand(commands, "Validation", "QUALITY", "Chạy CHECK PROJECT.", Sub() ProjectCheckClicked(Nothing, EventArgs.Empty))
        AddPaletteCommand(commands, "Commit", "TRANSACTION", "Commit staged changes.", Sub() CommitPendingClicked(Nothing, EventArgs.Empty))
        AddPaletteCommand(commands, "Health Check", "SYSTEM", "Kiểm tra cache/structure integrity.", Sub() HealthCheckClicked(Nothing, EventArgs.Empty))
        AddPaletteCommand(commands, "Recover UI", "SYSTEM", "Khôi phục Grid/UI an toàn.", Sub() RecoverUiClicked(Nothing, EventArgs.Empty))
        AddPaletteCommand(commands, "Final Regression Check", "SYSTEM", "Kiểm tra Production Release.", Sub() FinalRegressionClicked(Nothing, EventArgs.Empty))

        Using f As New BomCommandPaletteForm(commands)
            f.ShowDialog(Me)
        End Using
    End Sub

    Private Sub AddPaletteCommand(ByVal list As List(Of BomCommandItem),
                                  ByVal name As String,
                                  ByVal category As String,
                                  ByVal description As String,
                                  ByVal action As Action)
        Dim cmd As New BomCommandItem()
        cmd.Name = name
        cmd.Category = category
        cmd.Description = description
        cmd.ExecuteAction = action
        list.Add(cmd)
    End Sub

    Private Sub QuickFilterClicked(ByVal sender As Object, ByVal e As EventArgs)
        Select Case _quickFilterMode
            Case "ALL" : _quickFilterMode = "ERROR"
            Case "ERROR" : _quickFilterMode = "PURCHASED"
            Case "PURCHASED" : _quickFilterMode = "MANUFACTURE"
            Case "MANUFACTURE" : _quickFilterMode = "REFERENCE"
            Case Else : _quickFilterMode = "ALL"
        End Select
        ApplyQuickFilter()
    End Sub

    Private Sub ApplyQuickFilter()
        For Each row As DataGridViewRow In Grid.Rows
            If row Is Nothing Then Continue For
            Dim item As PartBomItem = TryCast(row.Tag, PartBomItem)
            If item Is Nothing Then
                row.Visible = (_quickFilterMode = "ALL")
                Continue For
            End If

            Dim visible As Boolean = True
            Select Case _quickFilterMode
                Case "ERROR"
                    visible = String.Equals(item.DataStatus, "ERROR", StringComparison.OrdinalIgnoreCase) OrElse
                              String.Equals(item.DataStatus, "WARNING", StringComparison.OrdinalIgnoreCase)
                Case "PURCHASED"
                    visible = BomStructurePolicy.IsPurchased(item)
                Case "MANUFACTURE"
                    visible = Not BomStructurePolicy.IsPurchased(item) AndAlso Not BomStructurePolicy.IsReference(item)
                Case "REFERENCE"
                    visible = BomStructurePolicy.IsReference(item)
                Case Else
                    visible = True
            End Select
            row.Visible = visible
        Next
        Text = Text.Split(New String() {"  | FILTER:"}, StringSplitOptions.None)(0) & "  | FILTER: " & _quickFilterMode
    End Sub

    Private Sub ReportCenterClicked(ByVal sender As Object, ByVal e As EventArgs)
        Dim report As BomReportTable = BomReportingEngine.BuildBomReport(_assemblyName, _allItems)
        Using f As New BomReportCenterForm(report)
            f.ShowDialog(Me)
        End Using
    End Sub

    Private Sub ReportCsvClicked(ByVal sender As Object, ByVal e As EventArgs)
        Dim report As BomReportTable = BomReportingEngine.BuildBomReport(_assemblyName, _allItems)
        Using dlg As New SaveFileDialog()
            dlg.Title = "EXPORT BOM REPORT CSV"
            dlg.Filter = "CSV (*.csv)|*.csv"
            dlg.FileName = "BOM_REPORT_" & DateTime.Now.ToString("yyyyMMdd_HHmmss") & ".csv"
            If dlg.ShowDialog(Me) <> DialogResult.OK Then Exit Sub
            Try
                BomReportingEngine.ExportCsv(report, dlg.FileName)
                MessageBox.Show("Đã xuất:" & System.Environment.NewLine & dlg.FileName, "REPORT", MessageBoxButtons.OK, MessageBoxIcon.Information)
            Catch ex As Exception
                BomLogger.Log("REPORT", dlg.FileName, "CSV", "ERROR", ex.Message)
                MessageBox.Show(ex.Message, "REPORT", MessageBoxButtons.OK, MessageBoxIcon.Error)
            End Try
        End Using
    End Sub

    Private Sub ReportHtmlClicked(ByVal sender As Object, ByVal e As EventArgs)
        Dim report As BomReportTable = BomReportingEngine.BuildBomReport(_assemblyName, _allItems)
        Using dlg As New SaveFileDialog()
            dlg.Title = "EXPORT BOM REPORT HTML"
            dlg.Filter = "HTML (*.html)|*.html"
            dlg.FileName = "BOM_REPORT_" & DateTime.Now.ToString("yyyyMMdd_HHmmss") & ".html"
            If dlg.ShowDialog(Me) <> DialogResult.OK Then Exit Sub
            Try
                BomReportingEngine.ExportHtml(report, dlg.FileName)
                MessageBox.Show("Đã xuất:" & System.Environment.NewLine & dlg.FileName, "REPORT", MessageBoxButtons.OK, MessageBoxIcon.Information)
            Catch ex As Exception
                BomLogger.Log("REPORT", dlg.FileName, "HTML", "ERROR", ex.Message)
                MessageBox.Show(ex.Message, "REPORT", MessageBoxButtons.OK, MessageBoxIcon.Error)
            End Try
        End Using
    End Sub

    Private Sub ManufacturingSummaryClicked(ByVal sender As Object, ByVal e As EventArgs)
        Dim summary As BomManufacturingSummary = BomManufacturingEngine.Analyze(_allItems)
        Using f As New BomManufacturingDashboard(summary)
            f.ShowDialog(Me)
        End Using
    End Sub

    Private Sub ManufacturingExportClicked(ByVal sender As Object, ByVal e As EventArgs)
        Dim summary As BomManufacturingSummary = BomManufacturingEngine.Analyze(_allItems)
        Using dlg As New SaveFileDialog()
            dlg.Title = "EXPORT MANUFACTURING SUMMARY"
            dlg.Filter = "CSV (*.csv)|*.csv"
            dlg.FileName = "MANUFACTURING_SUMMARY_" & DateTime.Now.ToString("yyyyMMdd_HHmmss") & ".csv"
            If dlg.ShowDialog(Me) <> DialogResult.OK Then Exit Sub
            Try
                Using sw As New System.IO.StreamWriter(dlg.FileName, False, System.Text.Encoding.UTF8)
                    sw.WriteLine("MATERIAL,THICKNESS,PROCESS,UNIQUE PARTS,TOTAL QTY,MANUFACTURE,PURCHASE")
                    For Each g As BomManufacturingGroup In summary.Groups
                        sw.WriteLine(CsvChangeValue(g.Material) & "," &
                                     CsvChangeValue(g.Thickness) & "," &
                                     CsvChangeValue(g.ProcessName) & "," &
                                     g.PartCount.ToString() & "," &
                                     g.TotalQty.ToString() & "," &
                                     g.ManufacturedCount.ToString() & "," &
                                     g.PurchasedCount.ToString())
                    Next
                End Using
                MessageBox.Show("Đã xuất Manufacturing Summary:" & System.Environment.NewLine & dlg.FileName,
                                "MANUFACTURING", MessageBoxButtons.OK, MessageBoxIcon.Information)
            Catch ex As Exception
                BomLogger.Log("MANUFACTURING", dlg.FileName, "Export", "ERROR", ex.Message)
                MessageBox.Show(ex.Message, "MANUFACTURING", MessageBoxButtons.OK, MessageBoxIcon.Error)
            End Try
        End Using
    End Sub

    Private Sub CaptureSnapshotClicked(ByVal sender As Object, ByVal e As EventArgs)
        Dim defaultName As String = _assemblyName & "_" & DateTime.Now.ToString("yyyyMMdd_HHmmss")
        Dim name As String = Microsoft.VisualBasic.Interaction.InputBox(
            "Tên Snapshot:", "CAPTURE BOM SNAPSHOT", defaultName)
        If String.IsNullOrWhiteSpace(name) Then Exit Sub
        _activeSnapshot = BomChangeManagementEngine.Capture(name.Trim(), _assemblyName, _allItems)
        _lastChangeSet = Nothing
        MessageBox.Show("Đã tạo Snapshot: " & _activeSnapshot.Name &
                        System.Environment.NewLine & "Items: " & _activeSnapshot.Items.Count.ToString(),
                        "SNAPSHOT", MessageBoxButtons.OK, MessageBoxIcon.Information)
    End Sub

    Private Sub CompareSnapshotClicked(ByVal sender As Object, ByVal e As EventArgs)
        If _activeSnapshot Is Nothing Then
            MessageBox.Show("Chưa có Snapshot. Hãy nhấn SNAPSHOT trước.",
                            "BOM COMPARE", MessageBoxButtons.OK, MessageBoxIcon.Information)
            Exit Sub
        End If
        _lastChangeSet = BomChangeManagementEngine.Compare(_activeSnapshot, _allItems)
        Using f As New BomChangeSetForm(_lastChangeSet)
            f.ShowDialog(Me)
        End Using
    End Sub

    Private Sub ChangeReportClicked(ByVal sender As Object, ByVal e As EventArgs)
        If _lastChangeSet Is Nothing Then
            If _activeSnapshot Is Nothing Then
                MessageBox.Show("Chưa có Snapshot/Change Set.", "CHANGE REPORT",
                                MessageBoxButtons.OK, MessageBoxIcon.Information)
                Exit Sub
            End If
            _lastChangeSet = BomChangeManagementEngine.Compare(_activeSnapshot, _allItems)
        End If

        Using dlg As New SaveFileDialog()
            dlg.Title = "EXPORT CHANGE REPORT"
            dlg.Filter = "CSV (*.csv)|*.csv"
            dlg.FileName = "BOM_CHANGE_" & DateTime.Now.ToString("yyyyMMdd_HHmmss") & ".csv"
            If dlg.ShowDialog(Me) <> DialogResult.OK Then Exit Sub
            Try
                Using sw As New System.IO.StreamWriter(dlg.FileName, False, System.Text.Encoding.UTF8)
                    sw.WriteLine("CHANGE,PART NUMBER,FILE,FIELD,OLD VALUE,NEW VALUE")
                    For Each c As BomChangeRecord In _lastChangeSet.Changes
                        sw.WriteLine(CsvChangeValue(c.Kind.ToString()) & "," &
                                     CsvChangeValue(c.PartNumber) & "," &
                                     CsvChangeValue(c.FileName) & "," &
                                     CsvChangeValue(c.FieldName) & "," &
                                     CsvChangeValue(c.OldValue) & "," &
                                     CsvChangeValue(c.NewValue))
                    Next
                End Using
                MessageBox.Show("Đã xuất Change Report:" & System.Environment.NewLine & dlg.FileName,
                                "CHANGE REPORT", MessageBoxButtons.OK, MessageBoxIcon.Information)
            Catch ex As Exception
                BomLogger.Log("CHANGE", dlg.FileName, "Export Report", "ERROR", ex.Message)
                MessageBox.Show(ex.Message, "CHANGE REPORT", MessageBoxButtons.OK, MessageBoxIcon.Error)
            End Try
        End Using
    End Sub

    Private Function CsvChangeValue(ByVal value As String) As String
        Dim s As String = If(value, "")
        Return """" & s.Replace("""", """""") & """"
    End Function

    Private Sub ShowDependencyImpact(ByVal focusImpact As Boolean)
        Dim item As PartBomItem = GetCurrentItem()
        If item Is Nothing Then
            MessageBox.Show("Hãy chọn một Part.", If(focusImpact, "IMPACT ANALYSIS", "WHERE USED 2.0"),
                            MessageBoxButtons.OK, MessageBoxIcon.Information)
            Exit Sub
        End If

        Dim root As BomWhereUsedNode = Nothing
        Dim impact As BomImpactResult = Nothing
        If Not BomDependencyCache.TryGet(item, root, impact) Then
            root = BomWhereUsedEngine.BuildTree(item, _assemblyName)
            impact = BomWhereUsedEngine.AnalyzeImpact(item, _drawingIndex)
            BomDependencyCache.Put(item, root, impact)
        End If

        Using f As New BomDependencyForm(item, root, impact,
                                         AddressOf OpenDependencyDrawing,
                                         AddressOf LocateDependencyAssembly,
                                         AddressOf FilterBomByImpact)
            f.ShowDialog(Me)
        End Using
    End Sub

    Private Sub FilterBomByImpact(ByVal impact As BomImpactResult)
        If impact Is Nothing OrElse impact.Part Is Nothing Then Exit Sub
        Dim targetKey As String = BomDependencyCache.MakeKey(impact.Part)
        Grid.ClearSelection()
        Dim firstRow As Integer = -1
        For Each row As DataGridViewRow In Grid.Rows
            If row Is Nothing Then Continue For
            Dim rowItem As PartBomItem = TryCast(row.Tag, PartBomItem)
            If rowItem Is Nothing Then
                row.Visible = False
                Continue For
            End If
            Dim samePart As Boolean = String.Equals(BomDependencyCache.MakeKey(rowItem), targetKey, StringComparison.OrdinalIgnoreCase)
            row.Visible = samePart
            If samePart AndAlso firstRow < 0 Then firstRow = row.Index
        Next
        If firstRow >= 0 Then
            Try
                Grid.FirstDisplayedScrollingRowIndex = firstRow
                Grid.Rows(firstRow).Selected = True
            Catch
            End Try
        End If
    End Sub

    Private Sub OpenDependencyDrawing(ByVal drawingPath As String)
        If String.IsNullOrWhiteSpace(drawingPath) OrElse Not System.IO.File.Exists(drawingPath) Then
            MessageBox.Show("Không tìm thấy Drawing:" & System.Environment.NewLine & drawingPath,
                            "DRAWING DEPENDENCY", MessageBoxButtons.OK, MessageBoxIcon.Warning)
            Exit Sub
        End If
        Try
            _inventor.Documents.Open(drawingPath, True)
        Catch ex As Exception
            BomLogger.Log("DEPENDENCY", drawingPath, "Open Drawing", "ERROR", ex.Message)
            MessageBox.Show("Không mở được Drawing:" & System.Environment.NewLine & ex.Message,
                            "DRAWING DEPENDENCY", MessageBoxButtons.OK, MessageBoxIcon.Error)
        End Try
    End Sub

    Private Sub LocateDependencyAssembly(ByVal assemblyName As String)
        If String.IsNullOrWhiteSpace(assemblyName) Then Exit Sub
        For Each row As DataGridViewRow In Grid.Rows
            If row Is Nothing OrElse Not row.Visible Then Continue For
            Dim headerPath As String = TryCast(row.HeaderCell.Tag, String)
            If Not String.IsNullOrWhiteSpace(headerPath) Then
                Dim names() As String = headerPath.Trim().Trim("\"c).Split("\"c)
                If names.Length > 0 AndAlso String.Equals(names(names.Length - 1), assemblyName, StringComparison.OrdinalIgnoreCase) Then
                    Grid.ClearSelection()
                    row.Selected = True
                    If row.Cells.Count > 0 Then Grid.CurrentCell = row.Cells(0)
                    Try
                        Grid.FirstDisplayedScrollingRowIndex = row.Index
                    Catch
                    End Try
                    Exit Sub
                End If
            End If
        Next
        MessageBox.Show("Assembly này không có dòng đang hiển thị trong BOM hiện tại:" &
                        System.Environment.NewLine & assemblyName,
                        "LOCATE ASSEMBLY", MessageBoxButtons.OK, MessageBoxIcon.Information)
    End Sub

    Private Sub ShowProjectIntelligenceText(ByVal title As String, ByVal content As String)
        Using f As New Form()
            f.Text = title
            f.StartPosition = FormStartPosition.CenterParent
            f.Width = 760
            f.Height = 620
            f.MinimizeBox = False
            f.MaximizeBox = True
            Dim box As New System.Windows.Forms.TextBox()
            box.Multiline = True
            box.ReadOnly = True
            box.ScrollBars = ScrollBars.Both
            box.WordWrap = False
            box.Dock = DockStyle.Fill
            box.Font = New Font("Consolas", 10.0F)
            box.Text = content
            f.Controls.Add(box)
            f.ShowDialog(Me)
        End Using
    End Sub


'####################################################################
' SUBSECTION 15.20 - OCCURRENCE LOOKUP / ASSEMBLY TRAVERSAL
'####################################################################

    Private Function GetSourceAssemblyDocument() As AssemblyDocument
        Try
            Dim sourceAsm As AssemblyDocument = Nothing
            Try
                sourceAsm = CType(_inventor.Documents.ItemByName(_assemblyPath), AssemblyDocument)
            Catch
            End Try
            If sourceAsm Is Nothing AndAlso System.IO.File.Exists(_assemblyPath) Then
                Try
                    sourceAsm = CType(_inventor.Documents.Open(_assemblyPath, True), AssemblyDocument)
                Catch
                End Try
            End If
            Return sourceAsm
        Catch
            Return Nothing
        End Try
    End Function

    Private Function GetTargetOccurrences() As List(Of ComponentOccurrence)
        Dim result As New List(Of ComponentOccurrence)()
        Dim seen As New HashSet(Of String)(StringComparer.OrdinalIgnoreCase)
        Dim sourceAsm As AssemblyDocument = GetSourceAssemblyDocument()
        If sourceAsm Is Nothing Then Return result

        If Grid.CurrentRow IsNot Nothing AndAlso IsAssemblyHeaderRow(Grid.CurrentRow) Then
            Dim groupName As String = GetRowGroupName(Grid.CurrentRow)
            If String.Equals(groupName, _assemblyName, StringComparison.OrdinalIgnoreCase) Then
                For Each occ As ComponentOccurrence In sourceAsm.ComponentDefinition.Occurrences
                    AddUniqueOccurrence(result, seen, occ)
                Next
            Else
                CollectAssemblyOccurrences(sourceAsm.ComponentDefinition.Occurrences, groupName, result, seen)
            End If
        Else
            Dim selected As List(Of PartBomItem) = GetSelectedItems()
            For Each item As PartBomItem In selected
                If item Is Nothing OrElse item.Occurrences Is Nothing Then Continue For
                For Each occ As ComponentOccurrence In item.Occurrences
                    AddUniqueOccurrence(result, seen, occ)
                Next
            Next
        End If
        Return result
    End Function

    Private Sub AddUniqueOccurrence(ByVal result As List(Of ComponentOccurrence), ByVal seen As HashSet(Of String), ByVal occ As ComponentOccurrence)
        If occ Is Nothing Then Exit Sub
        Dim key As String = ""
        Try
            key = occ.Name & "|" & occ.GetHashCode().ToString()
        Catch
            key = Guid.NewGuid().ToString()
        End Try
        If seen.Add(key) Then result.Add(occ)
    End Sub

    Private Sub CollectAssemblyOccurrences(ByVal occurrences As ComponentOccurrences, ByVal targetAssemblyName As String, ByVal result As List(Of ComponentOccurrence), ByVal seen As HashSet(Of String))
        If occurrences Is Nothing Then Exit Sub
        For Each occ As ComponentOccurrence In occurrences
            Try
                If occ.DefinitionDocumentType = DocumentTypeEnum.kAssemblyDocumentObject Then
                    Dim displayName As String = ""
                    Try
                        displayName = IOPath.GetFileNameWithoutExtension(occ.Definition.Document.FullFileName)
                    Catch
                        displayName = IOPath.GetFileNameWithoutExtension(occ.Name)
                    End Try
                    If String.Equals(displayName, targetAssemblyName, StringComparison.OrdinalIgnoreCase) Then
                        AddUniqueOccurrence(result, seen, occ)
                    ElseIf Not occ.Suppressed Then
                        CollectAssemblyOccurrences(occ.SubOccurrences, targetAssemblyName, result, seen)
                    End If
                End If
            Catch
            End Try
        Next
    End Sub

    Private Sub CollectAllOccurrences(ByVal occurrences As ComponentOccurrences, ByVal result As List(Of ComponentOccurrence))
        If occurrences Is Nothing Then Exit Sub
        For Each occ As ComponentOccurrence In occurrences
            result.Add(occ)
            Try
                If occ.DefinitionDocumentType = DocumentTypeEnum.kAssemblyDocumentObject AndAlso Not occ.Suppressed Then
                    CollectAllOccurrences(occ.SubOccurrences, result)
                End If
            Catch
            End Try
        Next
    End Sub


'####################################################################
' SUBSECTION 15.21 - INVENTOR UPDATE / SAVE / VISIBILITY / SUPPRESS
'####################################################################

    Private Sub InventorUpdateClicked(ByVal sender As Object, ByVal e As EventArgs)
        If Not EnsureWriteAllowed("Inventor Update") Then Exit Sub
        Try
            Dim sourceAsm As AssemblyDocument = GetSourceAssemblyDocument()
            If sourceAsm Is Nothing Then Throw New Exception("Không tìm thấy Assembly nguồn đang mở.")
            sourceAsm.Activate()
            sourceAsm.Update2(True)
            StatusLoadTime.Text = "Inventor: Update hoàn tất " & DateTime.Now.ToString("HH:mm:ss")
        Catch ex As Exception
            MessageBox.Show("Không thể Update Assembly." & vbCrLf & ex.Message, "BOM TOOL PRO", MessageBoxButtons.OK, MessageBoxIcon.Error)
        End Try
    End Sub

    Private Sub InventorRebuildClicked(ByVal sender As Object, ByVal e As EventArgs)
        If Not EnsureWriteAllowed("Inventor Rebuild") Then Exit Sub
        Try
            Dim sourceAsm As AssemblyDocument = GetSourceAssemblyDocument()
            If sourceAsm Is Nothing Then Throw New Exception("Không tìm thấy Assembly nguồn đang mở.")
            sourceAsm.Activate()
            sourceAsm.Rebuild2(True)
            StatusLoadTime.Text = "Inventor: Rebuild hoàn tất " & DateTime.Now.ToString("HH:mm:ss")
        Catch ex As Exception
            MessageBox.Show("Không thể Rebuild Assembly." & vbCrLf & ex.Message, "BOM TOOL PRO", MessageBoxButtons.OK, MessageBoxIcon.Error)
        End Try
    End Sub

    Private Sub InventorSaveAllClicked(ByVal sender As Object, ByVal e As EventArgs)
        If Not EnsureWriteAllowed("Save All") Then Exit Sub
        Try
            Dim saved As Integer = 0
            Dim failed As Integer = 0
            For Each doc As Inventor.Document In _inventor.Documents
                Try
                    If doc.Dirty AndAlso Not String.IsNullOrWhiteSpace(doc.FullFileName) Then
                        doc.Save()
                        saved += 1
                    End If
                Catch
                    failed += 1
                End Try
            Next
            MessageBox.Show("Đã lưu: " & saved.ToString() & " document" & If(failed > 0, vbCrLf & "Không lưu được: " & failed.ToString(), ""), "SAVE ALL", MessageBoxButtons.OK, If(failed > 0, MessageBoxIcon.Warning, MessageBoxIcon.Information))
        Catch ex As Exception
            MessageBox.Show("Không thể Save All." & vbCrLf & ex.Message, "BOM TOOL PRO", MessageBoxButtons.OK, MessageBoxIcon.Error)
        End Try
    End Sub

    Private Sub ToggleOccurrenceVisibilityClicked(ByVal sender As Object, ByVal e As EventArgs)
        If Not EnsureWriteAllowed("Visibility Change") Then Exit Sub
        Dim targets As List(Of ComponentOccurrence) = GetTargetOccurrences()
        If targets.Count = 0 Then
            MessageBox.Show("Hãy chọn Part hoặc Assembly cần Ẩn/Hiện.", "BOM TOOL PRO", MessageBoxButtons.OK, MessageBoxIcon.Information)
            Exit Sub
        End If
        Dim makeVisible As Boolean = False
        For Each occ As ComponentOccurrence In targets
            Try
                If Not occ.Visible Then makeVisible = True : Exit For
            Catch
            End Try
        Next
        For Each occ As ComponentOccurrence In targets
            Try
                If Not occ.Suppressed Then occ.Visible = makeVisible
            Catch
            End Try
        Next
        Try
            _inventor.ActiveView.Update()
        Catch
        End Try
    End Sub

    Private Sub SuppressOccurrencesClicked(ByVal sender As Object, ByVal e As EventArgs)
        If Not EnsureWriteAllowed("Suppress") Then Exit Sub
        SetOccurrenceSuppression(True)
    End Sub

    Private Sub UnsuppressOccurrencesClicked(ByVal sender As Object, ByVal e As EventArgs)
        If Not EnsureWriteAllowed("Unsuppress") Then Exit Sub
        SetOccurrenceSuppression(False)
    End Sub

    Private Sub SetOccurrenceSuppression(ByVal suppressValue As Boolean)
        Dim targets As List(Of ComponentOccurrence) = GetTargetOccurrences()
        If targets.Count = 0 Then
            MessageBox.Show("Hãy chọn Part hoặc Assembly cần xử lý.", "BOM TOOL PRO", MessageBoxButtons.OK, MessageBoxIcon.Information)
            Exit Sub
        End If
        Dim success As Integer = 0
        Dim failed As Integer = 0
        For Each occ As ComponentOccurrence In targets
            Try
                If suppressValue Then
                    If Not occ.Suppressed Then occ.Suppress()
                Else
                    If occ.Suppressed Then occ.Unsuppress()
                End If
                success += 1
            Catch
                failed += 1
            End Try
        Next
        StatusLoadTime.Text = If(suppressValue, "Suppress: ", "Unsuppress: ") & success.ToString() & If(failed > 0, " | Lỗi: " & failed.ToString(), "")
    End Sub


'####################################################################
' SUBSECTION 15.22 - ISOLATE / GROUND / HIGHLIGHT / ZOOM
'####################################################################

    Private Sub IsolateOccurrencesClicked(ByVal sender As Object, ByVal e As EventArgs)
        If Not EnsureWriteAllowed("Isolate") Then Exit Sub
        Try
            Dim sourceAsm As AssemblyDocument = GetSourceAssemblyDocument()
            If sourceAsm Is Nothing Then Throw New Exception("Không tìm thấy Assembly nguồn.")
            Dim targets As List(Of ComponentOccurrence) = GetTargetOccurrences()
            If targets.Count = 0 Then Throw New Exception("Hãy chọn Part hoặc Assembly cần Isolate.")

            RestoreIsolationInternal()
            Dim targetSet As New HashSet(Of ComponentOccurrence)()
            For Each occ As ComponentOccurrence In targets
                targetSet.Add(occ)
            Next

            Dim allOcc As New List(Of ComponentOccurrence)()
            CollectAllOccurrences(sourceAsm.ComponentDefinition.Occurrences, allOcc)
            For Each occ As ComponentOccurrence In allOcc
                Try
                    _isolateOccurrences.Add(occ)
                    _isolateVisibility.Add(occ.Visible)
                    If Not occ.Suppressed Then occ.Visible = targetSet.Contains(occ)
                Catch
                End Try
            Next
            sourceAsm.Activate()
            Try
                _inventor.ActiveView.Fit()
            Catch
            End Try
            StatusLoadTime.Text = "Isolate: " & targets.Count.ToString() & " occurrence"
        Catch ex As Exception
            MessageBox.Show("Không thể Isolate." & vbCrLf & ex.Message, "BOM TOOL PRO", MessageBoxButtons.OK, MessageBoxIcon.Error)
        End Try
    End Sub

    Private Sub RestoreIsolationClicked(ByVal sender As Object, ByVal e As EventArgs)
        If Not EnsureWriteAllowed("Restore Visibility") Then Exit Sub
        RestoreIsolationInternal()
        Try
            _inventor.ActiveView.Update()
        Catch
        End Try
    End Sub

    Private Sub RestoreIsolationInternal()
        If _isolateOccurrences.Count = 0 Then Exit Sub
        Dim count As Integer = Math.Min(_isolateOccurrences.Count, _isolateVisibility.Count)
        For i As Integer = 0 To count - 1
            Try
                Dim occ As ComponentOccurrence = _isolateOccurrences(i)
                If occ IsNot Nothing AndAlso Not occ.Suppressed Then occ.Visible = _isolateVisibility(i)
            Catch
            End Try
        Next
        _isolateOccurrences.Clear()
        _isolateVisibility.Clear()
        StatusLoadTime.Text = "Đã khôi phục hiển thị"
    End Sub

    Private Sub ToggleGroundedClicked(ByVal sender As Object, ByVal e As EventArgs)
        If Not EnsureWriteAllowed("Ground/Unground") Then Exit Sub
        Dim targets As List(Of ComponentOccurrence) = GetTargetOccurrences()
        If targets.Count = 0 Then
            MessageBox.Show("Hãy chọn Part hoặc Assembly cần Ground/Unground.", "BOM TOOL PRO", MessageBoxButtons.OK, MessageBoxIcon.Information)
            Exit Sub
        End If
        Dim groundValue As Boolean = False
        For Each occ As ComponentOccurrence In targets
            Try
                If Not occ.Grounded Then groundValue = True : Exit For
            Catch
            End Try
        Next
        Dim success As Integer = 0
        For Each occ As ComponentOccurrence In targets
            Try
                occ.Grounded = groundValue
                success += 1
            Catch
            End Try
        Next
        StatusLoadTime.Text = If(groundValue, "Ground: ", "Unground: ") & success.ToString()
    End Sub

    Private Sub HighlightClicked(ByVal sender As Object, ByVal e As EventArgs)
        HighlightCurrent(False, False)
    End Sub

    Private Sub ZoomClicked(ByVal sender As Object, ByVal e As EventArgs)
        HighlightCurrent(True, False)
    End Sub

    Private Sub HighlightCurrent(ByVal zoomAfter As Boolean, ByVal silent As Boolean)
        If _syncingSelection Then Exit Sub
        Try
            _syncingSelection = True
            Dim sourceAsm As AssemblyDocument = GetSourceAssemblyDocument()
            If sourceAsm Is Nothing Then
                If Not silent Then MessageBox.Show("Assembly nguồn hiện không mở.", "BOM TOOL PRO", MessageBoxButtons.OK, MessageBoxIcon.Information)
                Exit Sub
            End If

            Try : sourceAsm.Activate() : Catch : End Try
            ClearBomHighlight(sourceAsm)
            Try : sourceAsm.SelectSet.Clear() : Catch : End Try

            Dim selectedOccurrences As New List(Of ComponentOccurrence)()
            Dim selectedRows As New List(Of DataGridViewRow)()
            For Each row As DataGridViewRow In Grid.SelectedRows
                If row IsNot Nothing AndAlso row.Visible Then selectedRows.Add(row)
            Next
            If selectedRows.Count = 0 AndAlso Grid.CurrentRow IsNot Nothing Then selectedRows.Add(Grid.CurrentRow)

            For Each row As DataGridViewRow In selectedRows
                If IsAssemblyHeaderRow(row) Then
                    Dim groupName As String = GetRowGroupName(row)
                    CollectAssemblyOccurrences(sourceAsm.ComponentDefinition.Occurrences, groupName, selectedOccurrences)
                Else
                    Dim item As PartBomItem = TryCast(row.Tag, PartBomItem)
                    If item Is Nothing Then Continue For
                    CollectItemOccurrences(sourceAsm, item, selectedOccurrences)
                End If
            Next

            Dim unique As New HashSet(Of String)(StringComparer.OrdinalIgnoreCase)
            For Each occ As ComponentOccurrence In selectedOccurrences
                If occ Is Nothing Then Continue For
                Try
                    If occ.Suppressed Then Continue For
                    Dim key As String = occ.Name
                    Try
                        Dim keyDoc As Inventor.Document = occ.ReferencedDocumentDescriptor.ReferencedDocument
                        If keyDoc IsNot Nothing Then key &= "|" & keyDoc.FullFileName
                    Catch
                    End Try
                    If unique.Contains(key) Then Continue For
                    unique.Add(key)
                    Try : sourceAsm.SelectSet.Select(occ) : Catch : End Try
                    AddOccurrenceToBomHighlight(sourceAsm, occ)
                Catch
                End Try
            Next

            If sourceAsm.SelectSet.Count = 0 Then
                If Not silent Then MessageBox.Show("Không tìm thấy đối tượng tương ứng trong Assembly nguồn.", "BOM TOOL PRO", MessageBoxButtons.OK, MessageBoxIcon.Information)
                Exit Sub
            End If

            If zoomAfter Then
                Try : _inventor.CommandManager.ControlDefinitions.Item("AppZoomSelectCmd").Execute() : Catch : End Try
            End If
            StatusSelection.Text = "Đã chọn " & sourceAsm.SelectSet.Count.ToString() & " occurrence trong Inventor"
        Catch ex As Exception
            If Not silent Then MessageBox.Show("Không thể Highlight đối tượng." & vbCrLf & ex.Message, "BOM TOOL PRO", MessageBoxButtons.OK, MessageBoxIcon.Error)
        Finally
            _syncingSelection = False
        End Try
    End Sub

    Private Sub ClearBomHighlight(ByVal sourceAsm As AssemblyDocument)
        Try
            If _bomHighlightSet IsNot Nothing Then _bomHighlightSet.Clear()
        Catch
            _bomHighlightSet = Nothing
        End Try
        If _bomHighlightSet Is Nothing AndAlso sourceAsm IsNot Nothing Then
            Try
                _bomHighlightSet = sourceAsm.CreateHighlightSet()
                Try : _bomHighlightSet.Color = _inventor.TransientObjects.CreateColor(255, 80, 40) : Catch : End Try
            Catch
                _bomHighlightSet = Nothing
            End Try
        End If
    End Sub

    Private Sub AddOccurrenceToBomHighlight(ByVal sourceAsm As AssemblyDocument, ByVal occ As ComponentOccurrence)
        Try
            If _bomHighlightSet Is Nothing Then ClearBomHighlight(sourceAsm)
            If _bomHighlightSet IsNot Nothing Then _bomHighlightSet.AddItem(occ)
        Catch
        End Try
    End Sub

    Private Sub CollectItemOccurrences(ByVal sourceAsm As AssemblyDocument, ByVal item As PartBomItem, ByVal result As List(Of ComponentOccurrence))
        If item Is Nothing Then Exit Sub
        If _highlightAllOccurrences Then
            SelectMatchingOccurrencesToList(sourceAsm.ComponentDefinition.Occurrences, item.FilePath, result)
        ElseIf item.Occurrences IsNot Nothing AndAlso item.Occurrences.Count > 0 Then
            result.Add(item.Occurrences(0))
        Else
            SelectMatchingOccurrencesToList(sourceAsm.ComponentDefinition.Occurrences, item.FilePath, result, 1)
        End If
    End Sub

    Private Sub CollectAssemblyOccurrences(ByVal occurrences As ComponentOccurrences, ByVal targetAssemblyName As String, ByVal result As List(Of ComponentOccurrence))
        For Each occ As ComponentOccurrence In occurrences
            Try
                If occ.Suppressed Then Continue For
                Dim doc As Inventor.Document = Nothing
                Try : doc = occ.ReferencedDocumentDescriptor.ReferencedDocument : Catch : Try : doc = occ.Definition.Document : Catch : End Try : End Try
                If doc Is Nothing Then Continue For
                If String.Equals(targetAssemblyName, _assemblyName, StringComparison.OrdinalIgnoreCase) Then
                    result.Add(occ)
                ElseIf doc.DocumentType = DocumentTypeEnum.kAssemblyDocumentObject Then
                    Dim docName As String = GetDocumentPartNumberOrFileName(doc)
                    Dim fileNameOnly As String = IOPath.GetFileNameWithoutExtension(doc.FullFileName)
                    If String.Equals(docName, targetAssemblyName, StringComparison.OrdinalIgnoreCase) OrElse String.Equals(fileNameOnly, targetAssemblyName, StringComparison.OrdinalIgnoreCase) Then
                        result.Add(occ)
                    Else
                        CollectAssemblyOccurrences(occ.SubOccurrences, targetAssemblyName, result)
                    End If
                End If
            Catch
            End Try
        Next
    End Sub

    Private Sub SelectMatchingOccurrencesToList(ByVal occurrences As ComponentOccurrences, ByVal targetPath As String, ByVal result As List(Of ComponentOccurrence), Optional ByVal maxCount As Integer = 0)
        For Each occ As ComponentOccurrence In occurrences
            If maxCount > 0 AndAlso result.Count >= maxCount Then Exit Sub
            Try
                If occ.Suppressed Then Continue For
                Dim doc As Inventor.Document = Nothing
                Try : doc = occ.ReferencedDocumentDescriptor.ReferencedDocument : Catch : Try : doc = occ.Definition.Document : Catch : End Try : End Try
                If doc Is Nothing Then Continue For
                If String.Equals(doc.FullFileName, targetPath, StringComparison.OrdinalIgnoreCase) Then
                    result.Add(occ)
                    If maxCount > 0 AndAlso result.Count >= maxCount Then Exit Sub
                End If
                If doc.DocumentType = DocumentTypeEnum.kAssemblyDocumentObject Then
                    SelectMatchingOccurrencesToList(occ.SubOccurrences, targetPath, result, maxCount)
                End If
            Catch
            End Try
        Next
    End Sub

    Private Sub SyncFromInventorClicked(ByVal sender As Object, ByVal e As EventArgs)
        SyncBomSelectionFromInventor(True)
    End Sub

    Private Sub InventorSyncTimerTick(ByVal sender As Object, ByVal e As EventArgs)
        If Not _syncInventorToBom OrElse _syncingSelection Then Exit Sub
        SyncBomSelectionFromInventor(False)
    End Sub

    Private Sub SyncBomSelectionFromInventor(ByVal force As Boolean)
        Try
            Dim sourceAsm As AssemblyDocument = GetSourceAssemblyDocument()
            If sourceAsm Is Nothing OrElse sourceAsm.SelectSet.Count = 0 Then Exit Sub
            Dim keys As New HashSet(Of String)(StringComparer.OrdinalIgnoreCase)
            For Each selectedObject As Object In sourceAsm.SelectSet
                Dim occ As ComponentOccurrence = TryCast(selectedObject, ComponentOccurrence)
                If occ Is Nothing Then Continue For
                Dim doc As Inventor.Document = Nothing
                Try : doc = occ.ReferencedDocumentDescriptor.ReferencedDocument : Catch : Try : doc = occ.Definition.Document : Catch : End Try : End Try
                If doc IsNot Nothing AndAlso Not String.IsNullOrEmpty(doc.FullFileName) Then keys.Add(doc.FullFileName)
            Next
            If keys.Count = 0 Then Exit Sub
            Dim signatureBuilder As New StringBuilder()
            For Each keyValue As String In keys
                signatureBuilder.Append(keyValue).Append("|")
            Next
            Dim signature As String = signatureBuilder.ToString()
            If Not force AndAlso String.Equals(signature, _lastInventorSelectionKey, StringComparison.OrdinalIgnoreCase) Then Exit Sub
            _lastInventorSelectionKey = signature

            _syncingSelection = True
            Grid.ClearSelection()
            Dim firstRow As DataGridViewRow = Nothing
            For Each row As DataGridViewRow In Grid.Rows
                Dim item As PartBomItem = TryCast(row.Tag, PartBomItem)
                If item IsNot Nothing AndAlso keys.Contains(item.FilePath) Then
                    row.Selected = True
                    If firstRow Is Nothing Then firstRow = row
                End If
            Next
            If firstRow IsNot Nothing Then
                Grid.CurrentCell = firstRow.Cells(0)
                Try : Grid.FirstDisplayedScrollingRowIndex = Math.Max(0, firstRow.Index - 2) : Catch : End Try
                UpdatePreviewFromCurrentRow()
                StatusSelection.Text = "Inventor → BOM: " & Grid.SelectedRows.Count.ToString() & " dòng"
            End If
        Catch
        Finally
            _syncingSelection = False
        End Try
    End Sub



    Private Function BuildRegistryContextMenu(ByVal target As String) As ContextMenuStrip
        Dim menu As New ContextMenuStrip()
        Dim groups As New Dictionary(Of String, ToolStripMenuItem)(StringComparer.OrdinalIgnoreCase)
        For Each cmd As BomCommandDefinition In BomCommandRegistry.AllCommands()
            If String.IsNullOrWhiteSpace(cmd.ContextTarget) OrElse Not String.Equals(cmd.ContextTarget, target, StringComparison.OrdinalIgnoreCase) Then Continue For
            Dim groupName As String = If(String.IsNullOrWhiteSpace(cmd.ContextGroup), "OTHER", cmd.ContextGroup)
            Dim parent As ToolStripMenuItem = Nothing
            If Not groups.TryGetValue(groupName, parent) Then
                parent = New ToolStripMenuItem(groupName)
                groups(groupName) = parent : menu.Items.Add(parent)
            End If
            Dim child As New ToolStripMenuItem(cmd.Caption)
            child.Tag = cmd : child.Enabled = Not (_safeMode AndAlso cmd.IsWriteOperation)
            If cmd.Handler IsNot Nothing Then AddHandler child.Click, cmd.Handler
            parent.DropDownItems.Add(child)
        Next
        Return menu
    End Function

    Private Function EnsureWriteAllowed(ByVal operationName As String,
                                        Optional ByVal commandType As BomCommandType = BomCommandType.WriteCommand) As Boolean
        If BomWriteGuard.EnsureWriteAllowed(_safeMode, operationName, commandType) Then Return True
        ShowSafeModeNotice(operationName)
        Return False
    End Function

    Private Sub PersistPendingTransaction()
        Try
            BomPendingTransactionStore.Save(_pendingRecoveryFile, _assemblyPath, _pendingTransaction)
        Catch ex As Exception
            BomLogger.Warn("RECOVERY", "Persist pending failed: " & ex.Message)
        End Try
    End Sub

    Private Function ResolvePropertyInfo(ByVal propertyKey As String, ByVal propertyName As String) As PropertyColumnInfo
        For Each p As PropertyColumnInfo In _selectedProperties
            If p Is Nothing Then Continue For
            If String.Equals(p.Key, propertyKey, StringComparison.OrdinalIgnoreCase) Then Return p
            If Not String.IsNullOrWhiteSpace(propertyName) AndAlso String.Equals(p.PropertyName, propertyName, StringComparison.OrdinalIgnoreCase) Then Return p
        Next
        'Recovery cho native/model setting.
        If Not String.IsNullOrWhiteSpace(propertyKey) AndAlso propertyKey.StartsWith(SystemSettingSetInternalName & "||", StringComparison.OrdinalIgnoreCase) Then
            Dim settingId As String = propertyKey.Substring((SystemSettingSetInternalName & "||").Length)
            Dim p As PropertyColumnInfo = MakeSystemSetting(settingId, If(String.IsNullOrWhiteSpace(propertyName), settingId, propertyName))
            Return p
        End If

        'Recovery cho Custom iProperty được tạo trực tiếp trong BOM nhưng chưa Commit trước khi đóng/crash.
        If Not String.IsNullOrWhiteSpace(propertyName) AndAlso Not String.IsNullOrWhiteSpace(propertyKey) Then
            Dim customPrefix As String = "{D5CDD505-2E9C-101B-9397-08002B2CF9AE}||"
            If propertyKey.StartsWith(customPrefix, StringComparison.OrdinalIgnoreCase) Then
                Dim p As New PropertyColumnInfo()
                p.PropertySetInternalName = "{D5CDD505-2E9C-101B-9397-08002B2CF9AE}"
                p.PropertySetDisplayName = "User Defined Properties"
                p.PropertyName = propertyName.Trim()
                p.Key = BuildPropertyKey(p.PropertySetInternalName, p.PropertyName)
                p.DisplayText = BuildPropertyDisplayText(p.PropertySetDisplayName, p.PropertyName)
                p.IsVirtualCustom = True
                Return p
            End If
        End If
        Return Nothing
    End Function

    Private Sub RestorePendingTransactionIfAvailable()
        If String.IsNullOrWhiteSpace(_pendingRecoveryFile) OrElse Not System.IO.File.Exists(_pendingRecoveryFile) Then Exit Sub
        Dim storedAssembly As String = ""
        Dim txName As String = ""
        Dim created As DateTime = DateTime.MinValue
        Dim recovered As List(Of BomPropertyChange) = BomPendingTransactionStore.Load(_pendingRecoveryFile, storedAssembly, txName, created)
        If recovered.Count = 0 Then Exit Sub
        If Not String.Equals(storedAssembly, _assemblyPath, StringComparison.OrdinalIgnoreCase) Then Exit Sub

        Dim valid As New List(Of BomPropertyChange)()
        For Each ch As BomPropertyChange In recovered
            Dim propertyName As String = ch.ErrorMessage
            ch.ErrorMessage = ""
            ch.PropertyInfo = ResolvePropertyInfo(ch.PropertyKey, propertyName)
            Dim item As PartBomItem = FindItemByDocumentKey(ch.DocumentKey)
            If item Is Nothing AndAlso Not String.IsNullOrWhiteSpace(ch.DocumentPath) Then
                For Each candidate As PartBomItem In _allItems
                    If candidate IsNot Nothing AndAlso String.Equals(candidate.FilePath, ch.DocumentPath, StringComparison.OrdinalIgnoreCase) Then
                        item = candidate
                        Exit For
                    End If
                Next
            End If
            If item Is Nothing OrElse ch.PropertyInfo Is Nothing OrElse (Not String.IsNullOrWhiteSpace(ch.DocumentPath) AndAlso Not System.IO.File.Exists(ch.DocumentPath)) Then
                ch.Status = "CONFLICT"
                ch.ErrorMessage = "Document/Property không còn khả dụng."
            Else
                Dim currentValue As String = ""
                Try
                    currentValue = Convert.ToString(ReadSinglePropertyValue(item.Document, ch.PropertyInfo))
                Catch ex As Exception
                    ch.Status = "CONFLICT"
                    ch.ErrorMessage = "Không đọc được Current Value: " & ex.Message
                End Try
                If ch.Status <> "CONFLICT" AndAlso Not String.Equals(currentValue, ch.OldValue, StringComparison.Ordinal) Then
                    ch.Status = "CONFLICT"
                    ch.ErrorMessage = "Current value đã thay đổi: " & currentValue
                ElseIf ch.Status <> "CONFLICT" Then
                    ch.Status = "READY"
                End If
            End If
            valid.Add(ch)
        Next

        Using f As New BomRecoveryForm(valid, created)
            Dim answer As DialogResult = f.ShowDialog(Me)
            If answer = DialogResult.OK AndAlso f.RestoreRequested Then
                _pendingTransaction = New BomTransaction()
                _pendingTransaction.Name = If(String.IsNullOrWhiteSpace(txName), "RECOVERED BOM EDIT", txName)
                _pendingTransaction.CreatedAt = If(created = DateTime.MinValue, DateTime.Now, created)
                For Each ch As BomPropertyChange In valid
                    If ch.Status = "READY" Then
                        ch.Status = "PENDING"
                        _pendingTransaction.Changes.Add(ch)
                    End If
                Next
                ApplyPendingVisualsFromTransaction()
                PersistPendingTransaction()
            ElseIf f.DiscardRequested Then
                BomPendingTransactionStore.Delete(_pendingRecoveryFile)
            End If
        End Using
    End Sub

    Private Function ReadSinglePropertyValue(ByVal doc As Inventor.Document, ByVal propertyInfo As PropertyColumnInfo) As Object
        If doc Is Nothing OrElse propertyInfo Is Nothing Then Return ""
        Try
            Dim setObj As Inventor.PropertySet = Nothing
            Try
                setObj = doc.PropertySets.Item(propertyInfo.PropertySetInternalName)
            Catch
                setObj = doc.PropertySets.Item(propertyInfo.PropertySetDisplayName)
            End Try
            If setObj Is Nothing Then Return ""
            Dim prop As Inventor.Property = Nothing
            Try
                prop = setObj.Item(propertyInfo.PropertyName)
            Catch
                Return ""
            End Try
            If prop Is Nothing OrElse prop.Value Is Nothing Then Return ""
            Return prop.Value
        Catch
            Return ""
        End Try
    End Function

    Private Sub ApplyPendingVisualsFromTransaction()
        For Each ch As BomPropertyChange In _pendingTransaction.Changes
            Dim item As PartBomItem = FindItemByDocumentKey(ch.DocumentKey)
            If item Is Nothing OrElse ch.PropertyInfo Is Nothing Then Continue For
            For Each row As DataGridViewRow In Grid.Rows
                Dim rowItem As PartBomItem = TryCast(row.Tag, PartBomItem)
                If rowItem Is Nothing OrElse Not String.Equals(rowItem.DocumentKey, ch.DocumentKey, StringComparison.OrdinalIgnoreCase) Then Continue For
                For Each col As DataGridViewColumn In Grid.Columns
                    Dim pi As PropertyColumnInfo = TryCast(col.Tag, PropertyColumnInfo)
                    If pi IsNot Nothing AndAlso String.Equals(pi.Key, ch.PropertyKey, StringComparison.OrdinalIgnoreCase) Then
                        row.Cells(col.Index).Value = ch.NewValue
                        row.Cells(col.Index).Style.BackColor = Color.FromArgb(255, 248, 200)
                        row.Cells(col.Index).ToolTipText = "RECOVERED PENDING | " & ch.OldValue & " -> " & ch.NewValue
                        Exit For
                    End If
                Next
            Next
        Next
        UpdatePendingCaption()
    End Sub

    Private Sub DiscardSpecificPendingChanges(ByVal changes As List(Of BomPropertyChange))
        If changes Is Nothing OrElse changes.Count = 0 Then Exit Sub
        For Each ch As BomPropertyChange In New List(Of BomPropertyChange)(changes)
            _pendingTransaction.Changes.Remove(ch)
        Next
        _pendingTransaction.Status = If(_pendingTransaction.Changes.Count > 0, "PENDING", "EMPTY")
        LoadRows()
        ApplyPendingVisualsFromTransaction()
        PersistPendingTransaction()
        UpdatePendingCaption()
    End Sub

    Private Sub ManufacturingPlateClicked(ByVal sender As Object, ByVal e As EventArgs)
        ShowManufacturingList(BomManufacturingType.Plate, "PLATE LIST")
    End Sub

    Private Sub ManufacturingProfileClicked(ByVal sender As Object, ByVal e As EventArgs)
        ShowManufacturingList(BomManufacturingType.Profile, "PROFILE CUT LIST")
    End Sub

    Private Sub ManufacturingTubeClicked(ByVal sender As Object, ByVal e As EventArgs)
        ShowManufacturingList(BomManufacturingType.Tube, "TUBE / PIPE LIST")
    End Sub

    Private Sub ManufacturingSheetMetalClicked(ByVal sender As Object, ByVal e As EventArgs)
        ShowManufacturingList(BomManufacturingType.SheetMetal, "SHEET METAL LIST")
    End Sub

    Private Sub ManufacturingPurchasedClicked(ByVal sender As Object, ByVal e As EventArgs)
        ShowManufacturingList(BomManufacturingType.Purchased, "PURCHASED LIST")
    End Sub

    Private Sub ManufacturingFastenerClicked(ByVal sender As Object, ByVal e As EventArgs)
        ShowManufacturingList(BomManufacturingType.Fastener, "FASTENER LIST")
    End Sub

    Private Sub ShowManufacturingList(ByVal mfgType As BomManufacturingType, ByVal title As String)
        Dim records As List(Of BomManufacturingRecord) = BomManufacturingListBuilder.BuildRecords(_allItems)
        records = BomManufacturingListBuilder.Filter(records, mfgType)
        Using f As New BomManufacturingListForm(title, records)
            f.ShowDialog(Me)
        End Using
    End Sub

    Private Sub ToggleSafeModeClicked(ByVal sender As Object, ByVal e As EventArgs)
        _safeMode = Not _safeMode
        UpdateSafeModeUI()
        BomLogger.Info("SAFE_MODE", If(_safeMode, "Safe Mode enabled", "Safe Mode disabled"))
    End Sub

    Private Sub UpdateSafeModeUI()
        If Grid IsNot Nothing Then Grid.ReadOnly = _safeMode
        If ToolBar IsNot Nothing Then
            For Each toolItem As System.Windows.Forms.ToolStripItem In ToolBar.Items
                Dim key As String = If(toolItem.Text, "").ToUpperInvariant()
                Dim isWrite As Boolean =
                    key.Contains("LƯU") OrElse key.Contains("SAVE") OrElse key.Contains("PASTE") OrElse key.Contains("FILL") OrElse
                    key.Contains("XÓA Ô") OrElse key.Contains("SUPPRESS") OrElse key.Contains("UNSUPPRESS") OrElse
                    key.Contains("GROUND") OrElse key.Contains("ẨN / HIỆN") OrElse key.Contains("ISOLATE") OrElse
                    key.Contains("RESTORE") OrElse key = "UPDATE" OrElse key = "REBUILD" OrElse key.Contains("COMMIT")
                If isWrite Then toolItem.Enabled = Not _safeMode
            Next
        End If
        If RibbonQuickBar IsNot Nothing Then
            For Each c As Control In RibbonQuickBar.Controls
                Dim b As Button = TryCast(c, Button)
                If b Is Nothing Then Continue For
                Dim key As String = If(b.Text, "").ToUpperInvariant()
                If key = "COMMIT" OrElse key = "UNDO" OrElse key = "REDO" Then b.Enabled = Not _safeMode
            Next
        End If
        If StatusSafeMode IsNot Nothing Then
            If _safeMode Then
                StatusSafeMode.Text = "SAFE MODE | READ ONLY"
                StatusSafeMode.ForeColor = Color.DarkOrange
            Else
                StatusSafeMode.Text = "EDIT MODE"
                StatusSafeMode.ForeColor = Color.FromArgb(55, 80, 90)
            End If
        End If
        UpdatePendingCaption()
    End Sub

    Private Sub ShowSafeModeNotice(ByVal operationName As String)
        If StatusSelection IsNot Nothing Then StatusSelection.Text = "SAFE MODE | READ ONLY | Blocked: " & operationName
        BomLogger.Warn("SAFE_MODE", "Blocked operation: " & operationName)
    End Sub

    Private Sub SaveSessionState()
        If Not _config.EnableSessionPersistence OrElse String.IsNullOrWhiteSpace(_sessionFile) Then Exit Sub
        Try
            Dim s As New BomSessionState()
            s.AssemblyPath = _assemblyPath
            s.DisplayMode = _bomDisplayMode.ToString()
            s.ScanMode = _scanMode.ToString()
            s.SearchText = If(SearchBox Is Nothing, "", SearchBox.Text)
            s.AssemblyFilter = If(AssemblyFilterBox Is Nothing, "", AssemblyFilterBox.Text)
            s.QuickFilter = _quickFilterMode
            s.ActiveWorkspace = _activeRibbonTab
            s.SafeMode = _safeMode
            s.RibbonCollapsed = _ribbonCollapsed
            s.DetailPanelVisible = (MainSplit IsNot Nothing AndAlso Not MainSplit.Panel2Collapsed)
            If MainSplit IsNot Nothing AndAlso Not MainSplit.Panel2Collapsed Then s.DetailPanelWidth = Math.Max(260, MainSplit.ClientSize.Width - MainSplit.SplitterDistance)
            s.SelectedProfile = _selectedColumnProfile
            If Me.WindowState = System.Windows.Forms.FormWindowState.Normal Then
                s.WindowWidth = Me.Width
                s.WindowHeight = Me.Height
                s.WindowLeft = Me.Left
                s.WindowTop = Me.Top
            End If
            s.Save(_sessionFile)
        Catch ex As Exception
            BomLogger.Warn("SESSION", "Save session failed: " & ex.Message)
        End Try
    End Sub

    Private Sub RestoreSessionState()
        If Not _config.EnableSessionPersistence OrElse String.IsNullOrWhiteSpace(_sessionFile) Then Exit Sub
        Try
            Dim s As BomSessionState = BomSessionState.Load(_sessionFile)
            If Not String.IsNullOrWhiteSpace(s.AssemblyPath) AndAlso
               Not String.Equals(s.AssemblyPath, _assemblyPath, StringComparison.OrdinalIgnoreCase) Then Exit Sub

            _safeMode = s.SafeMode
            _ribbonCollapsed = s.RibbonCollapsed
            _detailPanelVisible = s.DetailPanelVisible
            _detailPanelWidth = Math.Max(260, s.DetailPanelWidth)
            _selectedColumnProfile = s.SelectedProfile
            If MainSplit IsNot Nothing Then
                MainSplit.Panel2Collapsed = Not _detailPanelVisible
                If _detailPanelVisible AndAlso MainSplit.ClientSize.Width > _detailPanelWidth Then SafeSetSplitterDistance(MainSplit, MainSplit.ClientSize.Width - _detailPanelWidth)
            End If
            ApplyRibbonCollapsedState()
            If SearchBox IsNot Nothing Then SearchBox.Text = s.SearchText
            If AssemblyFilterBox IsNot Nothing AndAlso Not String.IsNullOrWhiteSpace(s.AssemblyFilter) Then AssemblyFilterBox.Text = s.AssemblyFilter
            If Not String.IsNullOrWhiteSpace(s.QuickFilter) Then _quickFilterMode = s.QuickFilter
            If Not String.IsNullOrWhiteSpace(s.ActiveWorkspace) AndAlso _ribbonTabButtons.ContainsKey(s.ActiveWorkspace) Then
                _activeRibbonTab = s.ActiveWorkspace
                BuildToolBar()
                UpdateRibbonTabVisuals()
            End If
            If s.WindowWidth >= Me.MinimumSize.Width AndAlso s.WindowHeight >= Me.MinimumSize.Height Then
                Me.Size = New Size(s.WindowWidth, s.WindowHeight)
            End If
        Catch ex As Exception
            BomLogger.Warn("SESSION", "Restore session failed: " & ex.Message)
        End Try
    End Sub

    Private Sub BomViewerFormClosed(ByVal sender As Object, ByVal e As FormClosedEventArgs)
        BomViewerRegistry.Unregister(Me)
        PersistPendingTransaction()
        SaveSessionState()
        Try
            If _inventorSyncTimer IsNot Nothing Then _inventorSyncTimer.Stop()
        Catch
        End Try
        Try
            If _bomHighlightSet IsNot Nothing Then _bomHighlightSet.Clear()
        Catch ex As Exception
            BomLogger.Add(BomLogLevel.Warning, "VIEWER_CLOSE", ex.Message)
        End Try
        _bomHighlightSet = Nothing
        BomLogger.Info("VIEWER", "Viewer closed")
    End Sub

    Private Sub SelectMatchingAssemblyOccurrences(ByVal occurrences As ComponentOccurrences, ByVal targetAssemblyName As String, ByVal selectSet As SelectSet)
        For Each occ As ComponentOccurrence In occurrences
            Try
                If occ.Suppressed Then Continue For
                Dim doc As Inventor.Document = Nothing
                Try
                    doc = occ.ReferencedDocumentDescriptor.ReferencedDocument
                Catch
                    Try
                        doc = occ.Definition.Document
                    Catch
                    End Try
                End Try
                If doc Is Nothing Then Continue For
                If doc.DocumentType = DocumentTypeEnum.kAssemblyDocumentObject Then
                    Dim docName As String = GetDocumentPartNumberOrFileName(doc)
                    Dim fileNameOnly As String = IOPath.GetFileNameWithoutExtension(doc.FullFileName)
                    If String.Equals(docName, targetAssemblyName, StringComparison.OrdinalIgnoreCase) OrElse String.Equals(fileNameOnly, targetAssemblyName, StringComparison.OrdinalIgnoreCase) Then
                        selectSet.Select(occ)
                    Else
                        SelectMatchingAssemblyOccurrences(occ.SubOccurrences, targetAssemblyName, selectSet)
                    End If
                End If
            Catch
            End Try
        Next
    End Sub

    Private Sub SelectMatchingOccurrences(ByVal occurrences As ComponentOccurrences, ByVal targetPath As String, ByVal selectSet As SelectSet)
        For Each occ As ComponentOccurrence In occurrences
            Try
                If occ.Suppressed Then Continue For
                Dim doc As Inventor.Document = Nothing
                Try
                    doc = occ.ReferencedDocumentDescriptor.ReferencedDocument
                Catch
                    Try
                        doc = occ.Definition.Document
                    Catch
                    End Try
                End Try
                If doc IsNot Nothing Then
                    If doc.DocumentType = DocumentTypeEnum.kPartDocumentObject Then
                        If String.Equals(doc.FullFileName, targetPath, StringComparison.OrdinalIgnoreCase) Then selectSet.Select(occ)
                    ElseIf doc.DocumentType = DocumentTypeEnum.kAssemblyDocumentObject Then
                        SelectMatchingOccurrences(occ.SubOccurrences, targetPath, selectSet)
                    End If
                End If
            Catch
            End Try
        Next
    End Sub


    Private Function BeginBusy(ByVal operationName As String) As Boolean
        If _isBusy Then
            StatusSelection.Text = "Đang xử lý: " & _busyOperation
            Return False
        End If
        _isBusy = True
        _busyOperation = operationName
        Me.UseWaitCursor = True
        If ToolBar IsNot Nothing Then ToolBar.Enabled = False
        If RibbonHost IsNot Nothing Then RibbonHost.Enabled = False
        StatusSelection.Text = "Đang xử lý: " & operationName
        Return True
    End Function

    Private Sub EndBusy(Optional ByVal statusText As String = "Sẵn sàng")
        _isBusy = False
        _busyOperation = ""
        Me.UseWaitCursor = False
        If ToolBar IsNot Nothing Then ToolBar.Enabled = True
        If RibbonHost IsNot Nothing Then RibbonHost.Enabled = True
        StatusSelection.Text = statusText
    End Sub

    Private Sub RefreshViewFromCache()
        Dim sw As Stopwatch = Stopwatch.StartNew()
        _runtimeIndex.Build(_assemblyName, _allItems)
        BuildAssemblyFilterItems()
        LoadRows()
        _lastRefreshDurationMs = sw.ElapsedMilliseconds
        BomLogger.Info("REFRESH_VIEW", "Cache refresh in " & _lastRefreshDurationMs.ToString() & " ms")
    End Sub

'####################################################################
' SUBSECTION 15.23 - LOAD BOM / CACHE INFO / REFRESH
'####################################################################

    Private Sub LoadBomClicked(ByVal sender As Object, ByVal e As EventArgs)
        'The Viewer must never call the External Rule again.
        'Assembly switching is initiated by the user activating the target
        'Assembly in Inventor and running the BOM command/rule once.
        Try
            Dim activeDoc As Inventor.Document = _inventor.ActiveDocument
            If activeDoc Is Nothing OrElse activeDoc.DocumentType <> DocumentTypeEnum.kAssemblyDocumentObject Then
                MessageBox.Show("Hãy Active một Assembly (.iam) cần nạp.", "LOAD BOM", MessageBoxButtons.OK, MessageBoxIcon.Information)
                Exit Sub
            End If

            Dim activeAsm As AssemblyDocument = CType(activeDoc, AssemblyDocument)
            Dim activePath As String = activeAsm.FullFileName

            If String.Equals(BomViewerRegistry.NormalizePath(activePath),
                             BomViewerRegistry.NormalizePath(_assemblyPath),
                             StringComparison.OrdinalIgnoreCase) Then
                StatusSelection.Text = "Assembly này đang được BOM Tool quản lý. Không reload."
                Me.BringToFront()
                Me.Activate()
                Exit Sub
            End If

            MessageBox.Show( _
                "Assembly đang Active khác BOM hiện tại." & vbCrLf & vbCrLf & _
                "Current BOM:" & vbCrLf & _assemblyPath & vbCrLf & vbCrLf & _
                "Active Assembly:" & vbCrLf & activePath & vbCrLf & vbCrLf & _
                "Chạy lại lệnh BOM Tool một lần để mở workflow chuyển Assembly an toàn.", _
                "ASSEMBLY SWITCH", _
                MessageBoxButtons.OK, _
                MessageBoxIcon.Information)
        Catch ex As Exception
            BomLogger.Error("ASSEMBLY_SWITCH", "Load BOM command failed: " & ex.Message)
        End Try
    End Sub

    Private Sub ScanModeClicked(ByVal sender As Object, ByVal e As EventArgs)
        Using f As New BomScanModeForm(_scanMode)
            If f.ShowDialog(Me) <> DialogResult.OK Then Exit Sub
            Dim newMode As BomScanMode = f.SelectedMode
            If newMode = _scanMode Then Exit Sub
            _scanMode = newMode
        End Using

        _performance.LastMode = _scanMode.ToString().ToUpperInvariant()
        If _scanMode = BomScanMode.Fast Then
            _drawingIndex.Clear()
        Else
            BuildDrawingIndex()
        End If

        If _scanMode = BomScanMode.Deep Then
            Dim ctx As New BomOperationContext()
            ctx.OperationName = "DEEP SCAN"
            ctx.Total = _allItems.Count
            BeginBusy("DEEP SCAN")
            Try
                Dim i As Integer = 0
                For Each item As PartBomItem In _allItems
                    If ctx.CancelRequested Then Exit For
                    BomGeometryEngine.EnsureLoaded(item)
                    i += 1
                    ctx.Current = i
                    If i Mod 25 = 0 Then
                        StatusSelection.Text = "DEEP SCAN " & i.ToString() & " / " & ctx.Total.ToString()
                        WinFormsApplication.DoEvents()
                    End If
                Next
            Finally
                EndBusy()
            End Try
        End If

        SourceLabel.Text = "Nguồn: " & _assemblyPath & "  |  MODE: " & _scanMode.ToString().ToUpperInvariant()
        LoadRows()
        StatusSelection.Text = "Scan Mode: " & _scanMode.ToString().ToUpperInvariant()
    End Sub

    Private Sub ClearGeometryCacheClicked(ByVal sender As Object, ByVal e As EventArgs)
        Dim cleared As Integer = 0
        For Each item As PartBomItem In _allItems
            If item Is Nothing Then Continue For
            If String.Equals(item.GeometryLoadState, "LOADED", StringComparison.OrdinalIgnoreCase) OrElse _
               String.Equals(item.GeometryLoadState, "FAILED", StringComparison.OrdinalIgnoreCase) Then
                BomGeometryEngine.Invalidate(item)
                cleared += 1
            End If
            Dim geoKeys() As String = {"GEOMETRY_TYPE", "THICKNESS", "THICK_SOURCE", "BOUNDING_BOX", "MASS", "VOLUME", "SURFACE_AREA", "DENSITY"}
            For Each k As String In geoKeys
                item.LoadedFeatures.Remove(k)
                If item.FeatureValues.ContainsKey(k) Then item.FeatureValues.Remove(k)
            Next
        Next
        GC.Collect()
        StatusSelection.Text = "Đã xóa Geometry Cache: " & cleared.ToString() & " Part"
        LoadRows()
    End Sub

    Private Sub ClearThumbnailCacheClicked(ByVal sender As Object, ByVal e As EventArgs)
        For Each pair As KeyValuePair(Of String, System.Drawing.Image) In _thumbnailCache
            Try
                If pair.Value IsNot Nothing Then pair.Value.Dispose()
            Catch
            End Try
        Next
        Dim count As Integer = _thumbnailCache.Count
        _thumbnailCache.Clear()
        For Each item As PartBomItem In _allItems
            If item Is Nothing Then Continue For
            item.LoadedFeatures.Remove("THUMBNAIL")
            If item.FeatureValues.ContainsKey("THUMBNAIL") Then item.FeatureValues.Remove("THUMBNAIL")
        Next
        If PreviewImage IsNot Nothing Then PreviewImage.Image = Nothing
        GC.Collect()
        StatusSelection.Text = "Đã xóa Thumbnail Cache: " & count.ToString() & " ảnh"
    End Sub

    Private Sub ResetPerformanceCountersClicked(ByVal sender As Object, ByVal e As EventArgs)
        BomPerformanceCounters.Reset()
        _performance = New BomPerformanceSnapshot()
        _performance.LastMode = _scanMode.ToString().ToUpperInvariant()
        StatusSelection.Text = "Đã reset Performance Counter"
    End Sub

    Private Sub CacheInfoClicked(ByVal sender As Object, ByVal e As EventArgs)
        Try
            Dim assemblyCount As Integer = _runtimeIndex.ItemsByAssembly.Count
            Dim propertyCount As Integer = If(_selectedProperties Is Nothing, 0, _selectedProperties.Count)
            Dim occurrenceCount As Integer = _runtimeIndex.TotalOccurrences
            Dim message As New StringBuilder()
            message.AppendLine("BOM TOOL PRO - CACHE STATUS")
            message.AppendLine()
            message.AppendLine("Assembly index: " & assemblyCount.ToString())
            message.AppendLine("Unique Part: " & _runtimeIndex.ItemByKey.Count.ToString())
            message.AppendLine("Total QTY: " & _runtimeIndex.TotalQuantity.ToString())
            message.AppendLine("Cached Occurrence: " & occurrenceCount.ToString())
            message.AppendLine("Cached iProperty columns: " & propertyCount.ToString())
            message.AppendLine("Loaded at: " & _loadedAt.ToString("dd/MM/yyyy HH:mm:ss"))
            message.AppendLine("Last Refresh: " & _lastRefreshDurationMs.ToString() & " ms")
            message.AppendLine("Scan Mode: " & _scanMode.ToString().ToUpperInvariant())
            message.AppendLine("Signature checks: " & _performance.SignatureChecks.ToString())
            message.AppendLine("Cache hit: " & _performance.CacheHits.ToString() & " | miss: " & _performance.CacheMisses.ToString())
            message.AppendLine("Cache hit rate: " & _performance.HitRate().ToString("0.0") & " %")
            message.AppendLine("Changed documents (last smart refresh): " & _performance.ChangedDocuments.ToString())
            message.AppendLine()
            message.AppendLine("PERFORMANCE PROFILER")
            message.AppendLine("Initial BOM load: " & BomPerformanceCounters.InitialLoadMs.ToString() & " ms")
            message.AppendLine("Occurrence traversal: " & BomPerformanceCounters.OccurrenceTraversal.ToString())
            message.AppendLine("Document access: " & BomPerformanceCounters.DocumentAccess.ToString())
            message.AppendLine("Property read: " & BomPerformanceCounters.PropertyRead.ToString() & " | " & BomPerformanceCounters.PropertyReadMs.ToString() & " ms")
            message.AppendLine("Signature checks: " & BomPerformanceCounters.SignatureChecks.ToString())
            message.AppendLine("Geometry loads: " & BomPerformanceCounters.GeometryLoads.ToString() & " | " & BomPerformanceCounters.GeometryMs.ToString() & " ms")
            message.AppendLine("Drawing searches: " & BomPerformanceCounters.DrawingSearch.ToString() & " | index " & BomPerformanceCounters.DrawingIndexMs.ToString() & " ms")
            message.AppendLine("Grid refresh: " & BomPerformanceCounters.GridRefresh.ToString() & " | " & BomPerformanceCounters.GridBuildMs.ToString() & " ms")
            Dim memory As BomMemorySnapshot = BomMemorySnapshot.Capture(_allItems, occurrenceCount, _thumbnailCache.Count)
            message.AppendLine()
            message.AppendLine("MEMORY MONITOR")
            message.AppendLine("Managed: " & BomMemorySnapshot.FormatMB(memory.ManagedBytes))
            message.AppendLine("Inventor process working set: " & BomMemorySnapshot.FormatMB(memory.WorkingSetBytes))
            message.AppendLine("Cached Items: " & memory.CachedItems.ToString())
            message.AppendLine("Cached Occurrences: " & memory.CachedOccurrences.ToString())
            message.AppendLine("Cached Geometry: " & memory.CachedGeometry.ToString())
            message.AppendLine("Cached Thumbnails: " & memory.CachedThumbnails.ToString())
            Dim dirtyCount As Integer = 0
            For Each cacheItem As PartBomItem In _allItems
                If cacheItem IsNot Nothing AndAlso cacheItem.IsBomDirty Then dirtyCount += 1
            Next
            message.AppendLine("Dirty Part: " & dirtyCount.ToString())
            message.AppendLine(BomLogger.Summary())
            message.AppendLine()
            message.Append("Search, Filter, Dashboard, Project Check và Export đang dùng dữ liệu RAM đã Cache." & vbCrLf & vbCrLf & "Refresh thường = SMART INCREMENTAL | Ctrl+Refresh = đọc lại toàn bộ iProperty | Shift+Refresh = FULL RELOAD")
            MessageBox.Show(message.ToString(), "BOM TOOL PRO", MessageBoxButtons.OK, MessageBoxIcon.Information)
        Catch ex As Exception
            MessageBox.Show("Không thể đọc thông tin Cache." & vbCrLf & ex.Message, "BOM TOOL PRO", MessageBoxButtons.OK, MessageBoxIcon.Warning)
        End Try
    End Sub

    Private Function SmartIncrementalRefresh() As Boolean
        Dim sw As Stopwatch = Stopwatch.StartNew()
        Dim changed As New List(Of PartBomItem)()
        _performance.SignatureChecks = 0
        _performance.CacheHits = 0
        _performance.CacheMisses = 0
        _performance.ChangedDocuments = 0
        _performance.LastMode = _scanMode.ToString().ToUpperInvariant()

        'Nếu Assembly gốc đã thay đổi/Dirty, cấu trúc NEW/REMOVED/QTY có thể đã đổi.
        'Khi đó không đoán: chuyển sang Full Reload để bảo toàn tính đúng của BOM.
        Dim rootChanged As Boolean = False
        Try
            Dim activeAsm As AssemblyDocument = TryCast(_inventor.ActiveDocument, AssemblyDocument)
            If activeAsm IsNot Nothing AndAlso String.Equals(activeAsm.FullFileName, _assemblyPath, StringComparison.OrdinalIgnoreCase) Then
                If activeAsm.Dirty Then rootChanged = True
            End If
        Catch
        End Try
        If Not String.Equals(_rootAssemblySignature, BomSignatureEngine.FileSignature(_assemblyPath), StringComparison.Ordinal) Then rootChanged = True

        If rootChanged Then
            BomLogger.Info("SMART_REFRESH", "Root assembly changed -> FULL RELOAD")
            Return False
        End If

        For Each item As PartBomItem In _allItems
            If item Is Nothing Then Continue For
            _performance.SignatureChecks += 1
            BomPerformanceCounters.SignatureChecks += 1
            If BomSignatureEngine.HasChanged(item) Then
                item.LastCacheState = "CHANGED"
                changed.Add(item)
                _performance.CacheMisses += 1
            Else
                item.LastCacheState = "UNCHANGED"
                _performance.CacheHits += 1
            End If
        Next

        _performance.ChangedDocuments = changed.Count
        If changed.Count > 0 AndAlso _refreshCallback IsNot Nothing Then
            _refreshCallback.Invoke(changed)
            If _scanMode = BomScanMode.Deep Then
                For Each changedItem As PartBomItem In changed
                    BomGeometryEngine.EnsureLoaded(changedItem)
                Next
            End If
        End If
        _loadedAt = DateTime.Now
        RefreshViewFromCache()
        sw.Stop()
        _performance.SmartRefreshMs = sw.ElapsedMilliseconds
        _lastRefreshDurationMs = sw.ElapsedMilliseconds
        BomLogger.Info("SMART_REFRESH", "Checked=" & _performance.SignatureChecks.ToString() & ", changed=" & changed.Count.ToString() & ", hit=" & _performance.HitRate().ToString("0.0") & "%, time=" & sw.ElapsedMilliseconds.ToString() & " ms")
        Return True
    End Function

    Private Sub RefreshClicked(ByVal sender As Object, ByVal e As EventArgs)
        If Not BeginBusy("Refresh") Then Exit Sub
        Try
            Dim modifier As Keys = System.Windows.Forms.Control.ModifierKeys
            Dim sw As Stopwatch = Stopwatch.StartNew()

            If (modifier And Keys.Shift) = Keys.Shift Then
                'SHIFT + Refresh = quét lại toàn bộ Assembly bằng luồng LOAD BOM hiện có.
                EndBusy("Đang chuyển sang Full Reload...")
                If _loadBomCallback IsNot Nothing Then _loadBomCallback.Invoke()
                Exit Sub
            ElseIf (modifier And Keys.Control) = Keys.Control Then
                'CTRL + Refresh = đọc lại toàn bộ iProperty đã chọn.
                If _refreshCallback IsNot Nothing Then _refreshCallback.Invoke(_allItems)
                If _scanMode = BomScanMode.Deep Then
                    For Each deepRefreshItem As PartBomItem In _allItems
                        BomGeometryEngine.EnsureLoaded(deepRefreshItem)
                    Next
                End If
                _loadedAt = DateTime.Now
                RefreshViewFromCache()
                _lastRefreshDurationMs = sw.ElapsedMilliseconds
                EndBusy("Đã Refresh iProperty: " & _lastRefreshDurationMs.ToString() & " ms")
            Else
                'V20: SMART REFRESH = signature check; chỉ đọc lại Part thực sự thay đổi.
                Dim smartOk As Boolean = SmartIncrementalRefresh()
                If Not smartOk Then
                    EndBusy("Assembly đã thay đổi - đang Full Reload...")
                    If _loadBomCallback IsNot Nothing Then _loadBomCallback.Invoke()
                    Exit Sub
                End If
                EndBusy("Smart Refresh: " & _performance.ChangedDocuments.ToString() & " changed / " & _performance.SignatureChecks.ToString() & " checked | " & _lastRefreshDurationMs.ToString() & " ms")
            End If
        Catch ex As Exception
            BomLogger.Add(BomLogLevel.[Error], "REFRESH", ex.Message)
            EndBusy("Refresh lỗi")
            MessageBox.Show("Không thể Refresh." & vbCrLf & ex.Message, "BOM TOOL PRO", MessageBoxButtons.OK, MessageBoxIcon.Error)
        End Try
    End Sub

    Private Sub RefreshSelectedClicked(ByVal sender As Object, ByVal e As EventArgs)
        If _refreshCallback Is Nothing Then Exit Sub
        Dim rows As List(Of PartBomItem) = GetSelectedItems()
        If rows.Count = 0 Then Exit Sub
        If Not BeginBusy("Refresh dòng đã chọn") Then Exit Sub
        Try
            Dim sw As Stopwatch = Stopwatch.StartNew()
            _refreshCallback.Invoke(rows)
            _loadedAt = DateTime.Now
            LoadRows()
            _lastRefreshDurationMs = sw.ElapsedMilliseconds
            EndBusy("Đã Refresh " & rows.Count.ToString() & " dòng: " & _lastRefreshDurationMs.ToString() & " ms")
        Catch ex As Exception
            BomLogger.Add(BomLogLevel.[Error], "REFRESH_SELECTED", ex.Message)
            EndBusy("Refresh lỗi")
            MessageBox.Show("Không thể Refresh dòng đã chọn." & vbCrLf & ex.Message, "BOM TOOL PRO", MessageBoxButtons.OK, MessageBoxIcon.Error)
        End Try
    End Sub

    '================================================================
    ' MÁY TÍNH / THỐNG KÊ
    '================================================================

'####################################################################
' SUBSECTION 15.24 - CALCULATOR / ASSEMBLY OPEN / EXPORT COMMANDS
'####################################################################

    Private Sub CalculatorClicked(ByVal sender As Object, ByVal e As EventArgs)
        Dim assemblyRows As New List(Of PartBomItem)()
        If Grid.CurrentRow IsNot Nothing Then
            Dim groupName As String = GetRowGroupName(Grid.CurrentRow)
            If groupName.Length > 0 Then
                Dim seen As New HashSet(Of String)(StringComparer.OrdinalIgnoreCase)
                For Each row As DataGridViewRow In Grid.Rows
                    Dim item As PartBomItem = TryCast(row.Tag, PartBomItem)
                    If item IsNot Nothing AndAlso String.Equals(GetRowGroupName(row), groupName, StringComparison.OrdinalIgnoreCase) AndAlso Not seen.Contains(item.DocumentKey) Then
                        seen.Add(item.DocumentKey)
                        assemblyRows.Add(item)
                    End If
                Next
            End If
        End If
        Dim form As New BomCalculatorForm(New List(Of PartBomItem)(_allItems), GetFilteredItems(), GetSelectedItems(), assemblyRows, _selectedProperties)
        form.ShowDialog(Me)
        form.Dispose()
    End Sub

    Private Function GetCurrentAssemblyPath() As String
        If Grid.CurrentRow Is Nothing OrElse Not IsAssemblyHeaderRow(Grid.CurrentRow) Then Return ""
        Dim groupName As String = GetRowGroupName(Grid.CurrentRow)
        If String.Equals(groupName, _assemblyName, StringComparison.OrdinalIgnoreCase) Then Return _assemblyPath
        Dim sourceAsm As AssemblyDocument = Nothing
        Try
            sourceAsm = CType(_inventor.Documents.ItemByName(_assemblyPath), AssemblyDocument)
        Catch
        End Try
        If sourceAsm Is Nothing Then Return ""
        Return FindAssemblyPath(sourceAsm.ComponentDefinition.Occurrences, groupName)
    End Function

    Private Function FindAssemblyPath(ByVal occurrences As ComponentOccurrences, ByVal targetName As String) As String
        For Each occ As ComponentOccurrence In occurrences
            Try
                If occ.Suppressed Then Continue For
                Dim doc As Inventor.Document = Nothing
                Try : doc = occ.ReferencedDocumentDescriptor.ReferencedDocument : Catch : Try : doc = occ.Definition.Document : Catch : End Try : End Try
                If doc Is Nothing OrElse doc.DocumentType <> DocumentTypeEnum.kAssemblyDocumentObject Then Continue For
                Dim pn As String = GetDocumentPartNumberOrFileName(doc)
                Dim fn As String = IOPath.GetFileNameWithoutExtension(doc.FullFileName)
                If String.Equals(pn, targetName, StringComparison.OrdinalIgnoreCase) OrElse String.Equals(fn, targetName, StringComparison.OrdinalIgnoreCase) Then Return doc.FullFileName
                Dim nested As String = FindAssemblyPath(occ.SubOccurrences, targetName)
                If nested.Length > 0 Then Return nested
            Catch
            End Try
        Next
        Return ""
    End Function

    Private Sub OpenAssemblySelected()
        Dim path As String = GetCurrentAssemblyPath()
        If path.Length = 0 Then
            MessageBox.Show("Không tìm thấy file Assembly tương ứng.", "BOM TOOL PRO", MessageBoxButtons.OK, MessageBoxIcon.Information)
            Exit Sub
        End If
        Try
            _inventor.Documents.Open(path, True)
        Catch ex As Exception
            MessageBox.Show("Không mở được Assembly." & vbCrLf & ex.Message, "BOM TOOL PRO", MessageBoxButtons.OK, MessageBoxIcon.Error)
        End Try
    End Sub

    Private Sub ExportAllClicked(ByVal sender As Object, ByVal e As EventArgs)
        If _exportCallback IsNot Nothing Then _exportCallback.Invoke(New List(Of PartBomItem)(_allItems))
    End Sub

    Private Sub ExportSelectedClicked(ByVal sender As Object, ByVal e As EventArgs)
        If _exportCallback IsNot Nothing Then _exportCallback.Invoke(GetSelectedItems())
    End Sub

    Private Sub ExportFilteredClicked(ByVal sender As Object, ByVal e As EventArgs)
        If _exportCallback IsNot Nothing Then _exportCallback.Invoke(GetFilteredItems())
    End Sub
'####################################################################
' SECTION 15A - ON-DEMAND FEATURE ENGINE / THUMBNAIL / PREVIEW
' Chỉ đọc dữ liệu khi người dùng bật Feature. Bỏ chọn chỉ ẩn cột, Cache vẫn giữ.
'####################################################################

    Private Sub RegisterBuiltInFeatures()
        _featureRegistry.Clear()
        RegisterFeature(New BomFeatureDefinition("THUMBNAIL", "PART_IMAGE", "ẢNH PART", "PREVIEW", 92, True, True))
        RegisterFeature(New BomFeatureDefinition("GEOMETRY_TYPE", "GEOMETRY_TYPE", "DẠNG CHI TIẾT", "GEOMETRY", 125, False, False))
        RegisterFeature(New BomFeatureDefinition("THICKNESS", "THICKNESS", "THICK (" & BomUnitManager.LengthUnit & ")", "SHEET METAL", 92, True, False))
        RegisterFeature(New BomFeatureDefinition("THICK_SOURCE", "THICK_SOURCE", "NGUỒN THICK", "SHEET METAL", 110, True, False))
        RegisterFeature(New BomFeatureDefinition("BOUNDING_BOX", "BOUNDING_BOX", "BOUNDING BOX L x W x H (" & BomUnitManager.LengthUnit & ")", "PHYSICAL", 205, False, False))
        RegisterFeature(New BomFeatureDefinition("MASS", "FEATURE_MASS", "MASS (" & BomUnitManager.MassUnit & ")", "PHYSICAL", 100, True, False))
        RegisterFeature(New BomFeatureDefinition("VOLUME", "FEATURE_VOLUME", "VOLUME (" & BomUnitManager.VolumeUnit & ")", "PHYSICAL", 110, True, False))
        RegisterFeature(New BomFeatureDefinition("SURFACE_AREA", "FEATURE_AREA", "SURFACE AREA (" & BomUnitManager.AreaUnit & ")", "PHYSICAL", 125, True, False))
        RegisterFeature(New BomFeatureDefinition("DENSITY", "FEATURE_DENSITY", "DENSITY", "PHYSICAL", 100, True, False))
        RegisterFeature(New BomFeatureDefinition("FILE_SIZE", "FEATURE_FILE_SIZE", "FILE SIZE", "FILE", 100, True, False))
        RegisterFeature(New BomFeatureDefinition("LAST_MODIFIED", "FEATURE_LAST_MODIFIED", "LAST MODIFIED", "FILE", 145, True, False))
        RegisterFeature(New BomFeatureDefinition("READ_ONLY", "FEATURE_READONLY", "READ ONLY", "FILE", 82, True, False))
    End Sub

    Private Sub RegisterFeature(ByVal feature As BomFeatureDefinition)
        If feature Is Nothing OrElse String.IsNullOrWhiteSpace(feature.Key) Then Exit Sub
        _featureRegistry(feature.Key) = feature
    End Sub

    Private Sub FeatureManagerClicked(ByVal sender As Object, ByVal e As EventArgs)
        Dim form As New BomFeatureManagerForm(_featureRegistry, _enabledFeatures)
        If form.ShowDialog(Me) <> DialogResult.OK Then
            form.Dispose()
            Exit Sub
        End If
        ApplyFeatureSelection(form.SelectedFeatureKeys)
        form.Dispose()
    End Sub

    Private Sub ToggleThumbnailFeatureClicked(ByVal sender As Object, ByVal e As EventArgs)
        Dim nextKeys As New HashSet(Of String)(_enabledFeatures, StringComparer.OrdinalIgnoreCase)
        If nextKeys.Contains("THUMBNAIL") Then
            nextKeys.Remove("THUMBNAIL")
        Else
            nextKeys.Add("THUMBNAIL")
        End If
        ApplyFeatureSelection(nextKeys)
    End Sub

    Private Sub ApplyFeatureSelection(ByVal selectedKeys As IEnumerable(Of String))
        Dim requested As New HashSet(Of String)(StringComparer.OrdinalIgnoreCase)
        If selectedKeys IsNot Nothing Then
            For Each key As String In selectedKeys
                If _featureRegistry.ContainsKey(key) Then requested.Add(key)
            Next
        End If

        Me.Cursor = System.Windows.Forms.Cursors.WaitCursor
        Grid.SuspendLayout()
        Try
            'Chỉ Load những Feature mới được bật.
            For Each key As String In requested
                If Not _enabledFeatures.Contains(key) Then LoadFeatureForAllItems(key)
            Next
            _enabledFeatures = requested
            BuildColumns()
            LoadRows()
            If MainSplit IsNot Nothing Then
                MainSplit.Panel2Collapsed = Not _enabledFeatures.Contains("THUMBNAIL")
                If Not MainSplit.Panel2Collapsed Then
                    'Chờ WinForms bố trí lại Panel2 rồi mới đặt SplitterDistance.
                    Try
                        Me.BeginInvoke(New System.Windows.Forms.MethodInvoker(AddressOf ApplyDefaultSplitterDistance))
                    Catch
                        ApplyDefaultSplitterDistance()
                    End Try
                End If
            End If
            UpdatePreviewFromCurrentRow()
            BeginLoadVisibleThumbnails()
        Finally
            Grid.ResumeLayout()
            Me.Cursor = System.Windows.Forms.Cursors.Default
        End Try
    End Sub

    Private Sub LoadFeatureForAllItems(ByVal featureKey As String)
        If String.Equals(featureKey, "THUMBNAIL", StringComparison.OrdinalIgnoreCase) Then Exit Sub 'Lazy loading
        For Each item As PartBomItem In _allItems
            EnsureFeatureLoaded(item, featureKey)
        Next
    End Sub

    Private Sub EnsureFeatureLoaded(ByVal item As PartBomItem, ByVal featureKey As String)
        If item Is Nothing OrElse item.LoadedFeatures.Contains(featureKey) Then Exit Sub
        Try
            Select Case featureKey.ToUpperInvariant()
                Case "GEOMETRY_TYPE", "THICKNESS", "THICK_SOURCE", "BOUNDING_BOX", "MASS", "VOLUME", "SURFACE_AREA", "DENSITY"
                    BomGeometryEngine.EnsureLoaded(item)
            End Select
            Select Case featureKey.ToUpperInvariant()
                Case "GEOMETRY_TYPE"
                    item.FeatureValues(featureKey) = item.GeometryType
                Case "THICKNESS"
                    item.FeatureValues(featureKey) = item.Thickness
                Case "THICK_SOURCE"
                    item.FeatureValues(featureKey) = item.ThicknessSource
                Case "BOUNDING_BOX"
                    item.FeatureValues(featureKey) = item.BoundingBoxText
                Case "MASS"
                    item.FeatureValues(featureKey) = item.Mass
                Case "VOLUME"
                    item.FeatureValues(featureKey) = item.Volume
                Case "SURFACE_AREA"
                    item.FeatureValues(featureKey) = item.SurfaceArea
                Case "DENSITY"
                    Dim density As Double = 0
                    If item.Volume > 0 Then density = item.Mass / item.Volume
                    item.FeatureValues(featureKey) = density
                Case "FILE_SIZE"
                    If Not String.IsNullOrWhiteSpace(item.FilePath) AndAlso System.IO.File.Exists(item.FilePath) Then
                        item.FeatureValues(featureKey) = New System.IO.FileInfo(item.FilePath).Length
                    Else
                        item.FeatureValues(featureKey) = 0L
                    End If
                Case "LAST_MODIFIED"
                    If Not String.IsNullOrWhiteSpace(item.FilePath) AndAlso System.IO.File.Exists(item.FilePath) Then
                        item.FeatureValues(featureKey) = System.IO.File.GetLastWriteTime(item.FilePath)
                    Else
                        item.FeatureValues(featureKey) = Nothing
                    End If
                Case "READ_ONLY"
                    item.FeatureValues(featureKey) = item.IsReadOnly
            End Select
        Catch ex As Exception
            item.FeatureValues(featureKey) = "ERROR"
        Finally
            item.LoadedFeatures.Add(featureKey)
        End Try
    End Sub

    Private Function GetFeatureDisplayValue(ByVal item As PartBomItem, ByVal featureKey As String) As Object
        If item Is Nothing Then Return ""
        If String.Equals(featureKey, "THUMBNAIL", StringComparison.OrdinalIgnoreCase) Then
            Return GetThumbnailFromCache(item)
        End If
        EnsureFeatureLoaded(item, featureKey)
        If Not item.FeatureValues.ContainsKey(featureKey) Then Return ""
        Dim value As Object = item.FeatureValues(featureKey)
        Select Case featureKey.ToUpperInvariant()
            Case "THICKNESS"
                Return BomUnitManager.FormatLength(item.Thickness)
            Case "BOUNDING_BOX"
                Return BomUnitManager.FormatBoundingBox(item)
            Case "MASS"
                Return BomUnitManager.FormatMass(item.Mass)
            Case "VOLUME"
                Return BomUnitManager.FormatValue(BomUnitManager.ConvertVolumeFromCm3(item.Volume))
            Case "SURFACE_AREA"
                Return BomUnitManager.FormatValue(BomUnitManager.ConvertAreaFromCm2(item.SurfaceArea))
            Case "DENSITY"
                Dim d As Double = 0
                Double.TryParse(Convert.ToString(value), d)
                Return If(d = 0, "", d.ToString("0.####"))
            Case "FILE_SIZE"
                Dim bytes As Long = 0
                Long.TryParse(Convert.ToString(value), bytes)
                If bytes <= 0 Then Return ""
                If bytes >= 1048576 Then Return (bytes / 1048576.0).ToString("0.##") & " MB"
                Return (bytes / 1024.0).ToString("0.##") & " KB"
            Case "LAST_MODIFIED"
                If TypeOf value Is DateTime Then Return CType(value, DateTime).ToString("dd/MM/yyyy HH:mm")
            Case "READ_ONLY"
                Return If(Convert.ToBoolean(value), "YES", "NO")
        End Select
        Return If(value Is Nothing, "", value)
    End Function

    Private Function GetThumbnailFromCache(ByVal item As PartBomItem) As System.Drawing.Image
        If item Is Nothing Then Return Nothing
        If _thumbnailCache.ContainsKey(item.DocumentKey) Then Return _thumbnailCache(item.DocumentKey)
        Return Nothing
    End Function

    Private Sub BeginLoadVisibleThumbnails()
        If Not _enabledFeatures.Contains("THUMBNAIL") OrElse Grid.Rows.Count = 0 Then Exit Sub
        Dim first As Integer = 0
        Try : first = Grid.FirstDisplayedScrollingRowIndex : Catch : first = 0 : End Try
        If first < 0 Then first = 0
        Dim visible As Integer = Math.Max(20, Grid.DisplayedRowCount(True) + 4)
        For i As Integer = first To Math.Min(Grid.Rows.Count - 1, first + visible)
            Dim row As DataGridViewRow = Grid.Rows(i)
            Dim item As PartBomItem = TryCast(row.Tag, PartBomItem)
            If item Is Nothing Then Continue For
            Dim image As System.Drawing.Image = LoadThumbnailForItem(item)
            If Grid.Columns.Contains("PART_IMAGE") Then row.Cells("PART_IMAGE").Value = image
        Next
    End Sub

    Private Sub GridScrolledForLazyFeatures(ByVal sender As Object, ByVal e As System.Windows.Forms.ScrollEventArgs)
        BeginLoadVisibleThumbnails()
    End Sub

    Private Function LoadThumbnailForItem(ByVal item As PartBomItem) As System.Drawing.Image
        If item Is Nothing Then Return Nothing
        If _thumbnailCache.ContainsKey(item.DocumentKey) Then Return _thumbnailCache(item.DocumentKey)
        Dim image As System.Drawing.Image = Nothing
        Try
            If item.Document IsNot Nothing Then
                Dim thumbObject As Object = Nothing
                Try
                    thumbObject = item.Document.PropertySets.Item("Inventor Summary Information").Item("Thumbnail").Value
                Catch
                    Try : thumbObject = item.Document.PropertySets.Item("Summary Information").Item("Thumbnail").Value : Catch : End Try
                End Try
                image = PictureDispConverter.ToImage(thumbObject)
            End If
        Catch
            image = Nothing
        End Try
        If image Is Nothing Then image = CreateThumbnailPlaceholder(item.PartNumber)
        _thumbnailCache(item.DocumentKey) = image
        item.ThumbnailImage = image
        item.LoadedFeatures.Add("THUMBNAIL")
        Return image
    End Function

    Private Function CreateThumbnailPlaceholder(ByVal caption As String) As System.Drawing.Image
        Dim bmp As New System.Drawing.Bitmap(160, 120)
        Using g As System.Drawing.Graphics = System.Drawing.Graphics.FromImage(bmp)
            g.Clear(Color.FromArgb(242, 246, 248))
            Using pen As New System.Drawing.Pen(Color.FromArgb(160, 178, 186))
                g.DrawRectangle(pen, 1, 1, 157, 117)
            End Using
            Using f As New Font("Segoe UI", 8.5F, FontStyle.Bold)
                Dim txt As String = If(String.IsNullOrWhiteSpace(caption), "NO IMAGE", caption)
                g.DrawString(txt, f, System.Drawing.Brushes.DimGray, 8.0F, 46.0F)
            End Using
        End Using
        Return bmp
    End Function

    Private Sub BuildPreviewPanel()
        PreviewPanel = New Panel()
        PreviewPanel.Dock = DockStyle.Fill
        PreviewPanel.BackColor = Color.FromArgb(247, 250, 252)
        PreviewPanel.Padding = New System.Windows.Forms.Padding(10)

        PreviewTitle = New Label()
        PreviewTitle.Dock = DockStyle.Top
        PreviewTitle.Height = 34
        PreviewTitle.Font = New Font("Segoe UI Semibold", 11.0F, FontStyle.Bold)
        PreviewTitle.ForeColor = Color.FromArgb(38, 78, 98)
        PreviewTitle.Text = "SMART DETAIL"
        PreviewPanel.Controls.Add(PreviewTitle)

        PreviewImage = New PictureBox()
        PreviewImage.Dock = DockStyle.Top
        PreviewImage.Height = 170
        PreviewImage.SizeMode = System.Windows.Forms.PictureBoxSizeMode.Zoom
        PreviewImage.BackColor = Color.White
        PreviewImage.BorderStyle = System.Windows.Forms.BorderStyle.FixedSingle
        AddHandler PreviewImage.DoubleClick, AddressOf PreviewImageDoubleClicked
        PreviewPanel.Controls.Add(PreviewImage)

        DetailActions = New FlowLayoutPanel()
        DetailActions.Dock = DockStyle.Top
        DetailActions.Height = 38
        DetailActions.WrapContents = False
        DetailActions.Padding = New Padding(0, 5, 0, 2)
        AddDetailAction("OPEN", AddressOf OpenPartClicked)
        AddDetailAction("DRAWING", AddressOf OpenDrawingClicked)
        AddDetailAction("HIGHLIGHT", AddressOf HighlightClicked)
        AddDetailAction("ZOOM", AddressOf ZoomClicked)
        AddDetailAction("WHERE USED", AddressOf WhereUsedClicked)
        AddDetailAction("IMPACT", AddressOf ImpactAnalysisClicked)
        PreviewPanel.Controls.Add(DetailActions)

        DetailTabs = New TabControl()
        DetailTabs.Dock = DockStyle.Fill
        DetailTabs.Font = New Font("Segoe UI", 8.5F)
        PreviewPanel.Controls.Add(DetailTabs)

        Dim infoPage As New TabPage("DETAIL")
        PreviewInfo = New Label()
        PreviewInfo.Dock = DockStyle.Fill
        PreviewInfo.Padding = New Padding(8)
        PreviewInfo.AutoEllipsis = True
        PreviewInfo.Font = New Font("Segoe UI", 9.0F)
        PreviewInfo.Text = "Select a Part or Assembly."
        infoPage.Controls.Add(PreviewInfo)
        DetailTabs.TabPages.Add(infoPage)

        Dim propertyPage As New TabPage("PROPERTIES")
        DetailPropertyText = New TextBox()
        DetailPropertyText.Dock = DockStyle.Fill
        DetailPropertyText.Multiline = True
        DetailPropertyText.ReadOnly = True
        DetailPropertyText.ScrollBars = ScrollBars.Vertical
        DetailPropertyText.BorderStyle = BorderStyle.None
        propertyPage.Controls.Add(DetailPropertyText)
        DetailTabs.TabPages.Add(propertyPage)

        Dim contextPage As New TabPage("CONTEXT")
        DetailContextText = New TextBox()
        DetailContextText.Dock = DockStyle.Fill
        DetailContextText.Multiline = True
        DetailContextText.ReadOnly = True
        DetailContextText.ScrollBars = ScrollBars.Vertical
        DetailContextText.BorderStyle = BorderStyle.None
        contextPage.Controls.Add(DetailContextText)
        DetailTabs.TabPages.Add(contextPage)

        PreviewImage.BringToFront()
        DetailActions.BringToFront()
        PreviewTitle.BringToFront()
    End Sub

    Private Sub AddDetailAction(ByVal caption As String, ByVal handler As EventHandler)
        Dim b As New Button()
        b.Text = caption
        b.AutoSize = True
        b.Height = 27
        b.FlatStyle = FlatStyle.Flat
        b.FlatAppearance.BorderColor = Color.FromArgb(200, 215, 222)
        b.Font = New Font("Segoe UI", 7.5F, FontStyle.Bold)
        AddHandler b.Click, handler
        DetailActions.Controls.Add(b)
    End Sub

    Private Sub UpdatePreviewFromCurrentRow()
        If PreviewImage Is Nothing OrElse MainSplit Is Nothing OrElse MainSplit.Panel2Collapsed Then Exit Sub
        If Grid.CurrentRow Is Nothing Then Exit Sub
        Dim item As PartBomItem = TryCast(Grid.CurrentRow.Tag, PartBomItem)
        If item Is Nothing Then Exit Sub

        Dim img As System.Drawing.Image = LoadThumbnailForItem(item)
        PreviewImage.Image = img
        PreviewTitle.Text = If(String.IsNullOrWhiteSpace(item.PartNumber), item.FileName, item.PartNumber)

        Dim drawingState As String = GetDrawingStatus(item.FilePath)
        Dim mfg As String = "UNKNOWN"
        If item.IsPurchased Then mfg = "PURCHASED"
        If item.IsSheetMetal Then mfg = "SHEET METAL"

        PreviewInfo.Text =
            "PART INFORMATION" & vbCrLf & vbCrLf &
            "Part Number: " & item.PartNumber & vbCrLf &
            "Description: " & item.Description & vbCrLf &
            "Material: " & item.Material & vbCrLf &
            "Revision: " & item.Revision & vbCrLf &
            "Qty: " & item.Quantity.ToString() & vbCrLf &
            "Drawing: " & drawingState & vbCrLf &
            "Manufacturing: " & mfg & vbCrLf &
            "File: " & item.FileName

        If DetailPropertyText IsNot Nothing Then
            Dim p As New System.Text.StringBuilder()
            For Each pi As PropertyColumnInfo In _selectedProperties
                Dim value As String = ""
                If item.SelectedPropertyValues IsNot Nothing AndAlso item.SelectedPropertyValues.ContainsKey(pi.Key) Then value = item.SelectedPropertyValues(pi.Key)
                p.AppendLine(pi.PropertyName & ": " & value)
            Next
            DetailPropertyText.Text = p.ToString()
        End If

        If DetailContextText IsNot Nothing Then
            Dim contextTitle As String = _activeRibbonTab.ToUpperInvariant()
            Dim body As String = ""
            Select Case contextTitle
                Case "STRUCTURE" : body = "Parent: " & item.GetParentAssemblyText() & vbCrLf & "Where Used / Impact are available from this workspace."
                Case "CHECK" : body = "Validation status: " & If(String.Equals(item.DataStatus, "ERROR", StringComparison.OrdinalIgnoreCase), "ERROR", If(String.Equals(item.DataStatus, "WARNING", StringComparison.OrdinalIgnoreCase), "WARNING", "READY")) & vbCrLf & "Use CHECK PROJECT for full quality control."
                Case "DRAWINGS" : body = "Drawing status: " & drawingState & vbCrLf & "Path: " & FindDrawingPath(item.FilePath)
                Case "CHANGES" : body = "Pending property changes: " & _pendingTransaction.Changes.Count.ToString()
                Case "MANUFACTURING" : body = "Type: " & mfg & vbCrLf & "Material: " & item.Material & vbCrLf & "Thickness: " & BomUnitManager.FormatLength(item.Thickness)
                Case Else : body = "Current workspace: " & contextTitle
            End Select
            DetailContextText.Text = body
        End If
    End Sub

    Private Sub PreviewImageDoubleClicked(ByVal sender As Object, ByVal e As EventArgs)
        OpenPartClicked(sender, e)
    End Sub


End Class

'====================================================================
' FORM CHỌN THÊM IPROPERTY NGAY TRONG BOM VIEWER
'====================================================================


Public Class BomFeatureDefinition
    Public Key As String
    Public ColumnName As String
    Public HeaderText As String
    Public GroupName As String
    Public Width As Integer
    Public Centered As Boolean
    Public IsImage As Boolean
    Public Sub New(ByVal keyValue As String, ByVal columnValue As String, ByVal headerValue As String, ByVal groupValue As String, ByVal widthValue As Integer, ByVal centeredValue As Boolean, ByVal imageValue As Boolean)
        Key = keyValue : ColumnName = columnValue : HeaderText = headerValue : GroupName = groupValue
        Width = widthValue : Centered = centeredValue : IsImage = imageValue
    End Sub
End Class

Public Class BomFeatureManagerForm
    Inherits Form
    Private FeatureList As CheckedListBox
    Private Registry As Dictionary(Of String, BomFeatureDefinition)
    Public SelectedFeatureKeys As New HashSet(Of String)(StringComparer.OrdinalIgnoreCase)

    Public Sub New(ByVal registryValue As Dictionary(Of String, BomFeatureDefinition), ByVal enabledValue As HashSet(Of String))
        Registry = registryValue
        Me.Text = "FEATURE MANAGER - CHỈ LOAD KHI ĐƯỢC CHỌN"
        Me.StartPosition = FormStartPosition.CenterParent
        Me.Size = New Size(620, 650)
        Me.MinimumSize = New Size(520, 500)
        Me.Font = New Font("Segoe UI", 9.0F)

        Dim info As New Label()
        info.Dock = DockStyle.Top
        info.Height = 58
        info.Padding = New System.Windows.Forms.Padding(12, 10, 12, 4)
        info.Text = "Tick Feature cần dùng. Feature chưa chọn sẽ không hiện và không được đọc từ Inventor. Bỏ tick chỉ ẩn cột; Cache đã đọc vẫn được giữ."
        Me.Controls.Add(info)

        FeatureList = New CheckedListBox()
        FeatureList.Dock = DockStyle.Fill
        FeatureList.CheckOnClick = True
        FeatureList.HorizontalScrollbar = True
        Me.Controls.Add(FeatureList)
        FeatureList.BringToFront()

        Dim entries As New List(Of BomFeatureDefinition)(Registry.Values)
        entries.Sort(Function(a As BomFeatureDefinition, b As BomFeatureDefinition) As Integer
            Dim c As Integer = String.Compare(a.GroupName, b.GroupName, StringComparison.OrdinalIgnoreCase)
            If c <> 0 Then Return c
            Return String.Compare(a.HeaderText, b.HeaderText, StringComparison.OrdinalIgnoreCase)
        End Function)
        For Each f As BomFeatureDefinition In entries
            Dim display As String = "[" & f.GroupName & "]  " & f.HeaderText
            Dim index As Integer = FeatureList.Items.Add(New BomFeatureListItem(f.Key, display))
            If enabledValue IsNot Nothing AndAlso enabledValue.Contains(f.Key) Then FeatureList.SetItemChecked(index, True)
        Next

        Dim buttons As New Panel()
        buttons.Dock = DockStyle.Bottom
        buttons.Height = 52
        Me.Controls.Add(buttons)
        Dim okButton As New Button()
        okButton.Text = "ÁP DỤNG"
        okButton.Size = New Size(120, 32)
        okButton.Location = New Point(350, 10)
        okButton.Anchor = AnchorStyles.Top Or AnchorStyles.Right
        AddHandler okButton.Click, AddressOf ApplyClicked
        buttons.Controls.Add(okButton)
        Dim cancelButton As New Button()
        cancelButton.Text = "HỦY"
        cancelButton.Size = New Size(100, 32)
        cancelButton.Location = New Point(480, 10)
        cancelButton.Anchor = AnchorStyles.Top Or AnchorStyles.Right
        cancelButton.DialogResult = DialogResult.Cancel
        buttons.Controls.Add(cancelButton)
        Me.CancelButton = cancelButton
    End Sub

    Private Sub ApplyClicked(ByVal sender As Object, ByVal e As EventArgs)
        SelectedFeatureKeys.Clear()
        For Each obj As Object In FeatureList.CheckedItems
            Dim entry As BomFeatureListItem = TryCast(obj, BomFeatureListItem)
            If entry IsNot Nothing Then SelectedFeatureKeys.Add(entry.Key)
        Next
        Me.DialogResult = DialogResult.OK
        Me.Close()
    End Sub
End Class

Public Class BomFeatureListItem
    Public Key As String
    Public Text As String
    Public Sub New(ByVal keyValue As String, ByVal textValue As String)
        Key = keyValue : Text = textValue
    End Sub
    Public Overrides Function ToString() As String
        Return Text
    End Function
End Class

Public Class PictureDispConverter
    Inherits System.Windows.Forms.AxHost
    Private Sub New()
        MyBase.New("")
    End Sub
    Public Shared Function ToImage(ByVal pictureObject As Object) As System.Drawing.Image
        If pictureObject Is Nothing Then Return Nothing
        Try
            Dim image As System.Drawing.Image = CType(GetPictureFromIPicture(pictureObject), System.Drawing.Image)
            If image Is Nothing Then Return Nothing
            Return New System.Drawing.Bitmap(image)
        Catch
            Return Nothing
        End Try
    End Function
End Class




Public Enum BomAssemblySwitchDecision
    Cancel = 0
    KeepCurrent = 1
    LoadNew = 2
End Enum

Public Enum BomPendingSwitchDecision
    Cancel = 0
    Review = 1
    Commit = 2
    Discard = 3
End Enum

Public Class BomAssemblySwitchForm
    Inherits BomDialogBase
    Public Decision As BomAssemblySwitchDecision = BomAssemblySwitchDecision.Cancel

    Public Sub New(ByVal currentPath As String, ByVal newPath As String, ByVal pendingCount As Integer)
        Me.Text = "ASSEMBLY SWITCH"
        Me.Size = New Size(720, 390)
        SetHeader("BOM TOOL ĐANG QUẢN LÝ MỘT ASSEMBLY KHÁC",
                  "Tool sẽ không thay BOM hiện tại nếu bạn chưa xác nhận.")

        Dim content As New TableLayoutPanel()
        content.Dock = DockStyle.Fill
        content.ColumnCount = 2
        content.RowCount = 4
        content.ColumnStyles.Add(New ColumnStyle(SizeType.Absolute, 145))
        content.ColumnStyles.Add(New ColumnStyle(SizeType.Percent, 100))
        content.RowStyles.Add(New RowStyle(SizeType.Absolute, 72))
        content.RowStyles.Add(New RowStyle(SizeType.Absolute, 72))
        content.RowStyles.Add(New RowStyle(SizeType.Absolute, 48))
        content.RowStyles.Add(New RowStyle(SizeType.Percent, 100))

        content.Controls.Add(New Label() With {.Text = "CURRENT BOM", .Dock = DockStyle.Fill, .Padding = New Padding(8, 10, 8, 0), .Font = New Font("Segoe UI", 9.0F, FontStyle.Bold)}, 0, 0)
        content.Controls.Add(New Label() With {.Text = currentPath, .Dock = DockStyle.Fill, .Padding = New Padding(8, 10, 8, 0), .AutoEllipsis = True}, 1, 0)
        content.Controls.Add(New Label() With {.Text = "ACTIVE ASSEMBLY", .Dock = DockStyle.Fill, .Padding = New Padding(8, 10, 8, 0), .Font = New Font("Segoe UI", 9.0F, FontStyle.Bold)}, 0, 1)
        content.Controls.Add(New Label() With {.Text = newPath, .Dock = DockStyle.Fill, .Padding = New Padding(8, 10, 8, 0), .AutoEllipsis = True}, 1, 1)
        content.Controls.Add(New Label() With {.Text = "PENDING", .Dock = DockStyle.Fill, .Padding = New Padding(8, 10, 8, 0), .Font = New Font("Segoe UI", 9.0F, FontStyle.Bold)}, 0, 2)
        content.Controls.Add(New Label() With {.Text = pendingCount.ToString() & " changes", .Dock = DockStyle.Fill, .Padding = New Padding(8, 10, 8, 0), .ForeColor = If(pendingCount > 0, Color.DarkOrange, BomUiTheme.TextPrimary)}, 1, 2)

        ContentHost.Controls.Add(content)

        ActionBar.Controls.Add(BomUiFactory.ActionButton("CANCEL", Sub(sender, e) CloseWith(BomAssemblySwitchDecision.Cancel)))
        ActionBar.Controls.Add(BomUiFactory.ActionButton("KEEP CURRENT BOM", Sub(sender, e) CloseWith(BomAssemblySwitchDecision.KeepCurrent)))
        ActionBar.Controls.Add(BomUiFactory.ActionButton("LOAD NEW ASSEMBLY", Sub(sender, e) CloseWith(BomAssemblySwitchDecision.LoadNew), True))
    End Sub

    Private Sub CloseWith(ByVal value As BomAssemblySwitchDecision)
        Decision = value
        Me.DialogResult = DialogResult.OK
        Me.Close()
    End Sub
End Class

Public Class BomPendingSwitchForm
    Inherits BomDialogBase
    Public Decision As BomPendingSwitchDecision = BomPendingSwitchDecision.Cancel

    Public Sub New(ByVal pendingCount As Integer, ByVal assemblyName As String)
        Me.Text = "PENDING CHANGES"
        Me.Size = New Size(650, 330)
        SetHeader(pendingCount.ToString() & " THAY ĐỔI CHƯA ĐƯỢC COMMIT",
                  "Phải xử lý Pending Changes trước khi chuyển Assembly.")

        Dim info As New Label()
        info.Dock = DockStyle.Fill
        info.Padding = New Padding(16)
        info.Font = New Font("Segoe UI", 10.0F)
        info.Text = "Assembly hiện tại: " & assemblyName & vbCrLf & vbCrLf &
                    "Pending Changes sẽ không bao giờ bị xóa âm thầm." & vbCrLf &
                    "Chọn cách xử lý trước khi tiếp tục."
        ContentHost.Controls.Add(info)

        ActionBar.Controls.Add(BomUiFactory.ActionButton("CANCEL", Sub(sender, e) Choose(BomPendingSwitchDecision.Cancel)))
        ActionBar.Controls.Add(BomUiFactory.ActionButton("REVIEW", Sub(sender, e) Choose(BomPendingSwitchDecision.Review)))
        ActionBar.Controls.Add(BomUiFactory.ActionButton("DISCARD", Sub(sender, e) Choose(BomPendingSwitchDecision.Discard)))
        ActionBar.Controls.Add(BomUiFactory.ActionButton("COMMIT", Sub(sender, e) Choose(BomPendingSwitchDecision.Commit), True))
    End Sub

    Private Sub Choose(ByVal value As BomPendingSwitchDecision)
        Decision = value
        Me.DialogResult = DialogResult.OK
        Me.Close()
    End Sub
End Class


'####################################################################
' PRO MAX 2.0 - PENDING REVIEW / RECOVERY / MANUFACTURING / SCAN UI
'####################################################################
Public Class BomUiTheme
    Public Shared ReadOnly Background As Color = Color.FromArgb(246, 249, 251)
    Public Shared ReadOnly Surface As Color = Color.White
    Public Shared ReadOnly Border As Color = Color.FromArgb(210, 220, 226)
    Public Shared ReadOnly Accent As Color = Color.FromArgb(36, 112, 140)
    Public Shared ReadOnly TextPrimary As Color = Color.FromArgb(38, 52, 60)
    Public Shared ReadOnly TextSecondary As Color = Color.FromArgb(92, 108, 116)
    Public Shared ReadOnly UiFont As New Font("Segoe UI", 9.0F)
End Class

Public Class BomUiFactory
    Public Shared Function ActionButton(ByVal caption As String, ByVal handler As EventHandler) As Button
        Return ActionButton(caption, handler, False)
    End Function

    Public Shared Function ActionButton(ByVal caption As String, ByVal handler As EventHandler, ByVal isPrimary As Boolean) As Button
        Dim b As New Button()
        b.Text = caption
        b.AutoSize = True
        b.Height = 30
        b.Padding = New Padding(10, 0, 10, 0)
        b.FlatStyle = FlatStyle.Flat
        b.Font = BomUiTheme.UiFont
        b.FlatAppearance.BorderColor = BomUiTheme.Border
        If isPrimary Then
            b.BackColor = BomUiTheme.Accent
            b.ForeColor = Color.White
            b.FlatAppearance.BorderColor = BomUiTheme.Accent
        Else
            b.BackColor = BomUiTheme.Surface
            b.ForeColor = BomUiTheme.TextPrimary
        End If
        If handler IsNot Nothing Then AddHandler b.Click, handler
        Return b
    End Function
End Class

Public Class BomDialogBase
    Inherits Form

    Protected HeaderTitle As Label
    Protected HeaderSubtitle As Label
    Protected ContentHost As Panel
    Protected ActionBar As FlowLayoutPanel

    Public Sub New()
        Me.Font = BomUiTheme.UiFont
        Me.BackColor = BomUiTheme.Background
        Me.StartPosition = FormStartPosition.CenterParent
        Me.MinimizeBox = False
        Me.MaximizeBox = False
        Me.ShowInTaskbar = False

        Dim root As New TableLayoutPanel()
        root.Dock = DockStyle.Fill
        root.ColumnCount = 1
        root.RowCount = 3
        root.RowStyles.Add(New RowStyle(SizeType.Absolute, 82.0F))
        root.RowStyles.Add(New RowStyle(SizeType.Percent, 100.0F))
        root.RowStyles.Add(New RowStyle(SizeType.Absolute, 54.0F))
        Me.Controls.Add(root)

        Dim header As New Panel()
        header.Dock = DockStyle.Fill
        header.BackColor = BomUiTheme.Surface
        header.Padding = New Padding(16, 12, 16, 8)

        HeaderTitle = New Label()
        HeaderTitle.Dock = DockStyle.Top
        HeaderTitle.Height = 28
        HeaderTitle.Font = New Font("Segoe UI", 12.0F, FontStyle.Bold)
        HeaderTitle.ForeColor = BomUiTheme.TextPrimary

        HeaderSubtitle = New Label()
        HeaderSubtitle.Dock = DockStyle.Fill
        HeaderSubtitle.Font = BomUiTheme.UiFont
        HeaderSubtitle.ForeColor = BomUiTheme.TextSecondary
        HeaderSubtitle.Padding = New Padding(0, 3, 0, 0)

        header.Controls.Add(HeaderSubtitle)
        header.Controls.Add(HeaderTitle)
        root.Controls.Add(header, 0, 0)

        ContentHost = New Panel()
        ContentHost.Dock = DockStyle.Fill
        ContentHost.BackColor = BomUiTheme.Background
        ContentHost.Padding = New Padding(12)
        root.Controls.Add(ContentHost, 0, 1)

        ActionBar = New FlowLayoutPanel()
        ActionBar.Dock = DockStyle.Fill
        ActionBar.FlowDirection = FlowDirection.RightToLeft
        ActionBar.WrapContents = False
        ActionBar.Padding = New Padding(10, 10, 10, 8)
        ActionBar.BackColor = BomUiTheme.Surface
        root.Controls.Add(ActionBar, 0, 2)
    End Sub

    Protected Sub SetHeader(ByVal title As String, ByVal subtitle As String)
        HeaderTitle.Text = If(title, "")
        HeaderSubtitle.Text = If(subtitle, "")
    End Sub
End Class

Public Class BomStatusCard
    Inherits Panel
End Class
Public Class BomMetricCard
    Inherits Panel
End Class
Public Class BomSectionHeader
    Inherits Label
End Class
Public Class BomActionBar
    Inherits FlowLayoutPanel
End Class
Public Class BomEmptyState
    Inherits Label
End Class

Public Class BomPendingChangesForm
    Inherits BomDialogBase
    Private Grid As DataGridView
    Public ActionName As String = ""
    Public SelectedChanges As New List(Of BomPropertyChange)()

    Public Sub New(ByVal changes As List(Of BomPropertyChange))
        Me.Text = "PENDING CHANGES"
        Me.StartPosition = FormStartPosition.CenterParent
        Me.Size = New Size(940, 560)
        Me.MinimumSize = New Size(760, 420)
        Me.Font = New Font("Segoe UI", 9.0F)

        Dim FilterBar As New FlowLayoutPanel()
        FilterBar.Dock = DockStyle.Top : FilterBar.Height = 38 : FilterBar.WrapContents = False
        Dim PartFilter As New TextBox() : PartFilter.Width = 150
        Dim PropertyFilter As New TextBox() : PropertyFilter.Width = 150
        Dim StatusFilter As New ComboBox() : StatusFilter.Width = 120 : StatusFilter.DropDownStyle = ComboBoxStyle.DropDownList
        StatusFilter.Items.AddRange(New Object() {"ALL", "PENDING", "CONFLICT", "FAILED", "COMMITTED", "ROLLED BACK"}) : StatusFilter.SelectedIndex = 0
        FilterBar.Controls.Add(New Label() With {.Text = "Part", .AutoSize = True, .Padding = New Padding(0, 7, 0, 0)}) : FilterBar.Controls.Add(PartFilter)
        FilterBar.Controls.Add(New Label() With {.Text = "Property", .AutoSize = True, .Padding = New Padding(8, 7, 0, 0)}) : FilterBar.Controls.Add(PropertyFilter)
        FilterBar.Controls.Add(New Label() With {.Text = "Status", .AutoSize = True, .Padding = New Padding(8, 7, 0, 0)}) : FilterBar.Controls.Add(StatusFilter)

        Grid = New DataGridView()
        Grid.Dock = DockStyle.Fill
        Grid.AllowUserToAddRows = False
        Grid.AllowUserToDeleteRows = False
        Grid.SelectionMode = DataGridViewSelectionMode.FullRowSelect
        Grid.MultiSelect = True
        Grid.AutoSizeColumnsMode = DataGridViewAutoSizeColumnsMode.Fill
        Grid.RowHeadersVisible = False
        Grid.Columns.Add("PART", "PART")
        Grid.Columns.Add("PROPERTY", "PROPERTY")
        Grid.Columns.Add("OLD", "OLD")
        Grid.Columns.Add("NEW", "NEW")
        Grid.Columns.Add("STATUS", "STATUS")
        Grid.Columns.Add("DOCUMENT", "DOCUMENT")

        For Each ch As BomPropertyChange In changes
            Dim propName As String = If(ch.PropertyInfo Is Nothing, ch.PropertyKey, ch.PropertyInfo.PropertyName)
            Dim idx As Integer = Grid.Rows.Add(If(String.IsNullOrWhiteSpace(ch.PartNumber), ch.FileName, ch.PartNumber),
                                               propName, ch.OldValue, ch.NewValue, ch.Status, ch.FileName)
            Grid.Rows(idx).Tag = ch
        Next

        Dim buttons As New FlowLayoutPanel()
        buttons.Dock = DockStyle.Bottom
        buttons.Height = 48
        buttons.FlowDirection = FlowDirection.RightToLeft
        AddActionButton(buttons, "COMMIT ALL", "COMMIT_ALL")
        AddActionButton(buttons, "COMMIT SELECTED", "COMMIT_SELECTED")
        AddActionButton(buttons, "DISCARD ALL", "DISCARD_ALL")
        AddActionButton(buttons, "DISCARD SELECTED", "DISCARD_SELECTED")
        Dim closeButton As New Button()
        closeButton.Text = "CLOSE"
        closeButton.Size = New Size(95, 30)
        AddHandler closeButton.Click, Sub() Me.Close()
        buttons.Controls.Add(closeButton)

        AddHandler PartFilter.TextChanged, Sub() ApplyPendingFilter(PartFilter.Text, PropertyFilter.Text, Convert.ToString(StatusFilter.SelectedItem))
        AddHandler PropertyFilter.TextChanged, Sub() ApplyPendingFilter(PartFilter.Text, PropertyFilter.Text, Convert.ToString(StatusFilter.SelectedItem))
        AddHandler StatusFilter.SelectedIndexChanged, Sub() ApplyPendingFilter(PartFilter.Text, PropertyFilter.Text, Convert.ToString(StatusFilter.SelectedItem))
        Me.Controls.Add(Grid)
        Me.Controls.Add(FilterBar)
        Me.Controls.Add(buttons)
    End Sub

    Private Sub ApplyPendingFilter(ByVal partText As String, ByVal propertyText As String, ByVal statusText As String)
        Dim p As String = If(partText, "").Trim().ToUpperInvariant()
        Dim prop As String = If(propertyText, "").Trim().ToUpperInvariant()
        Dim st As String = If(statusText, "ALL").Trim().ToUpperInvariant()
        For Each row As DataGridViewRow In Grid.Rows
            Dim ok1 As Boolean = p = "" OrElse Convert.ToString(row.Cells("PART").Value).ToUpperInvariant().Contains(p)
            Dim ok2 As Boolean = prop = "" OrElse Convert.ToString(row.Cells("PROPERTY").Value).ToUpperInvariant().Contains(prop)
            Dim ok3 As Boolean = st = "ALL" OrElse Convert.ToString(row.Cells("STATUS").Value).ToUpperInvariant() = st
            row.Visible = ok1 AndAlso ok2 AndAlso ok3
        Next
    End Sub

    Private Sub AddActionButton(ByVal host As FlowLayoutPanel, ByVal caption As String, ByVal action As String)
        Dim b As New Button()
        b.Text = caption
        b.Tag = action
        b.AutoSize = True
        b.Height = 30
        AddHandler b.Click, AddressOf ActionClicked
        host.Controls.Add(b)
    End Sub

    Private Sub ActionClicked(ByVal sender As Object, ByVal e As EventArgs)
        Dim b As Button = TryCast(sender, Button)
        If b Is Nothing Then Exit Sub
        ActionName = Convert.ToString(b.Tag)
        SelectedChanges.Clear()
        For Each row As DataGridViewRow In Grid.SelectedRows
            Dim ch As BomPropertyChange = TryCast(row.Tag, BomPropertyChange)
            If ch IsNot Nothing Then SelectedChanges.Add(ch)
        Next
        If (ActionName = "COMMIT_SELECTED" OrElse ActionName = "DISCARD_SELECTED") AndAlso SelectedChanges.Count = 0 Then
            MessageBox.Show("Hãy chọn ít nhất một thay đổi.", "PENDING CHANGES", MessageBoxButtons.OK, MessageBoxIcon.Information)
            Exit Sub
        End If
        Me.DialogResult = DialogResult.OK
        Me.Close()
    End Sub
End Class

Public Class BomRecoveryForm
    Inherits BomDialogBase
    Private Grid As DataGridView
    Public RestoreRequested As Boolean = False
    Public DiscardRequested As Boolean = False

    Public Sub New(ByVal changes As List(Of BomPropertyChange), ByVal savedAt As DateTime)
        Me.Text = "SESSION RECOVERY"
        Me.StartPosition = FormStartPosition.CenterParent
        Me.Size = New Size(900, 520)
        Me.MinimumSize = New Size(720, 400)
        Me.Font = New Font("Segoe UI", 9.0F)

        Dim header As New Label()
        header.Dock = DockStyle.Top
        header.Height = 52
        header.Padding = New Padding(10)
        header.Text = "Previous session contains " & changes.Count.ToString() & " uncommitted changes." &
                      If(savedAt = DateTime.MinValue, "", "  Last saved: " & savedAt.ToString("yyyy-MM-dd HH:mm:ss"))

        Grid = New DataGridView()
        Grid.Dock = DockStyle.Fill
        Grid.ReadOnly = True
        Grid.AllowUserToAddRows = False
        Grid.RowHeadersVisible = False
        Grid.AutoSizeColumnsMode = DataGridViewAutoSizeColumnsMode.Fill
        Grid.Columns.Add("PART", "PART")
        Grid.Columns.Add("PROPERTY", "PROPERTY")
        Grid.Columns.Add("OLD", "STORED OLD")
        Grid.Columns.Add("PENDING", "RECOVERED")
        Grid.Columns.Add("STATUS", "STATUS")
        Grid.Columns.Add("DETAIL", "DETAIL")
        For Each ch As BomPropertyChange In changes
            Dim propName As String = If(ch.PropertyInfo Is Nothing, ch.PropertyKey, ch.PropertyInfo.PropertyName)
            Grid.Rows.Add(If(String.IsNullOrWhiteSpace(ch.PartNumber), ch.FileName, ch.PartNumber),
                          propName, ch.OldValue, ch.NewValue, ch.Status, ch.ErrorMessage)
        Next

        Dim buttons As New FlowLayoutPanel()
        buttons.Dock = DockStyle.Bottom
        buttons.Height = 48
        buttons.FlowDirection = FlowDirection.RightToLeft

        Dim restore As New Button()
        restore.Text = "RESTORE CHANGES"
        restore.AutoSize = True
        AddHandler restore.Click, Sub()
                                      RestoreRequested = True
                                      Me.DialogResult = DialogResult.OK
                                      Me.Close()
                                  End Sub
        buttons.Controls.Add(restore)

        Dim discard As New Button()
        discard.Text = "DISCARD"
        discard.AutoSize = True
        AddHandler discard.Click, Sub()
                                      DiscardRequested = True
                                      Me.DialogResult = DialogResult.Cancel
                                      Me.Close()
                                  End Sub
        buttons.Controls.Add(discard)

        Dim viewOnly As New Button()
        viewOnly.Text = "KEEP FOR LATER"
        viewOnly.AutoSize = True
        AddHandler viewOnly.Click, Sub() Me.Close()
        buttons.Controls.Add(viewOnly)

        Me.Controls.Add(Grid)
        Me.Controls.Add(header)
        Me.Controls.Add(buttons)
    End Sub
End Class

Public Class BomScanModeForm
    Inherits Form
    Private Combo As ComboBox
    Public SelectedMode As BomScanMode

    Public Sub New(ByVal currentMode As BomScanMode)
        SelectedMode = currentMode
        Me.Text = "SCAN MODE"
        Me.StartPosition = FormStartPosition.CenterParent
        Me.FormBorderStyle = FormBorderStyle.FixedDialog
        Me.MaximizeBox = False
        Me.MinimizeBox = False
        Me.ClientSize = New Size(430, 180)
        Me.Font = New Font("Segoe UI", 9.0F)

        Dim title As New Label()
        title.Text = "SCAN MODE"
        title.Font = New Font("Segoe UI", 11.0F, FontStyle.Bold)
        title.SetBounds(20, 18, 160, 28)

        Combo = New ComboBox()
        Combo.DropDownStyle = ComboBoxStyle.DropDownList
        Combo.Items.AddRange(New Object() {"FAST", "NORMAL", "DEEP"})
        Combo.SelectedIndex = CInt(currentMode)
        Combo.SetBounds(20, 52, 180, 28)

        Dim info As New Label()
        info.Text = "FAST  — Core BOM only, Geometry lazy." & vbCrLf &
                    "NORMAL — Standard workflow." & vbCrLf &
                    "DEEP  — Geometry + advanced analysis."
        info.SetBounds(215, 48, 200, 78)

        Dim ok As New Button()
        ok.Text = "APPLY"
        ok.SetBounds(250, 135, 75, 28)
        AddHandler ok.Click, Sub()
                                 SelectedMode = CType(Combo.SelectedIndex, BomScanMode)
                                 Me.DialogResult = DialogResult.OK
                                 Me.Close()
                             End Sub

        Dim cancel As New Button()
        cancel.Text = "CANCEL"
        cancel.SetBounds(335, 135, 75, 28)
        AddHandler cancel.Click, Sub() Me.Close()

        Me.Controls.Add(title)
        Me.Controls.Add(Combo)
        Me.Controls.Add(info)
        Me.Controls.Add(ok)
        Me.Controls.Add(cancel)
    End Sub
End Class

Public Class BomManufacturingListForm
    Inherits BomDialogBase
    Public Sub New(ByVal title As String, ByVal records As List(Of BomManufacturingRecord))
        Me.Text = title
        Me.StartPosition = FormStartPosition.CenterParent
        Me.Size = New Size(1080, 600)
        Me.MinimumSize = New Size(820, 440)
        Me.Font = New Font("Segoe UI", 9.0F)

        Dim grid As New DataGridView()
        grid.Dock = DockStyle.Fill
        grid.ReadOnly = True
        grid.AllowUserToAddRows = False
        grid.RowHeadersVisible = False
        grid.SelectionMode = DataGridViewSelectionMode.FullRowSelect
        grid.AutoSizeColumnsMode = DataGridViewAutoSizeColumnsMode.Fill
        grid.Columns.Add("PART", "PART NUMBER")
        grid.Columns.Add("DESC", "DESCRIPTION")
        grid.Columns.Add("MATERIAL", "MATERIAL")
        grid.Columns.Add("TYPE", "TYPE")
        grid.Columns.Add("CONFIDENCE", "CONFIDENCE")
        grid.Columns.Add("THK", "THICKNESS")
        grid.Columns.Add("WIDTH", "WIDTH")
        grid.Columns.Add("LENGTH", "LENGTH")
        grid.Columns.Add("QTY", "QTY")
        grid.Columns.Add("UNITMASS", "UNIT MASS")
        grid.Columns.Add("TOTALMASS", "TOTAL MASS")

        For Each r As BomManufacturingRecord In records
            grid.Rows.Add(r.PartNumber, r.Description, r.Material,
                          r.ManufacturingType.ToString().ToUpperInvariant(),
                          r.Confidence.ToString().ToUpperInvariant(),
                          BomUnitManager.FormatLength(r.Thickness),
                          BomUnitManager.FormatLength(r.Width),
                          BomUnitManager.FormatLength(r.Length),
                          r.Quantity,
                          BomUnitManager.FormatMass(r.UnitMass),
                          BomUnitManager.FormatMass(r.TotalMass))
        Next

        Dim status As New Label()
        status.Dock = DockStyle.Bottom
        status.Height = 30
        status.Padding = New Padding(8, 6, 8, 0)
        status.Text = records.Count.ToString() & " records | UNKNOWN values are intentionally not guessed."

        Me.Controls.Add(grid)
        Me.Controls.Add(status)
    End Sub
End Class



'####################################################################
' SECTION 16 - ADD PROPERTY FORM
' Form thêm và quản lý các cột iProperty động.
'####################################################################

Public Class BomAddPropertiesForm
    Inherits Form

    Private PropertyList As CheckedListBox
    Private SearchBox As TextBox
    Private CountLabel As Label
    Private CustomNameBox As TextBox
    Private AllProperties As List(Of PropertyColumnInfo)
    Private CheckedKeys As New HashSet(Of String)(StringComparer.OrdinalIgnoreCase)
    Public SelectedProperties As New List(Of PropertyColumnInfo)()

    Public Sub New(ByVal available As List(Of PropertyColumnInfo))
        AllProperties = If(available, New List(Of PropertyColumnInfo)())
        Me.Text = "THÊM iPROPERTY VÀO BOM"
        Me.StartPosition = FormStartPosition.CenterParent
        Me.Size = New Size(700, 650)
        Me.MinimumSize = New Size(580, 520)
        Me.Font = New Font("Segoe UI", 9.0F)
        Me.BackColor = Color.FromArgb(244, 250, 252)

        Dim topPanel As New Panel()
        topPanel.Dock = DockStyle.Top
        topPanel.Height = 140
        topPanel.Padding = New System.Windows.Forms.Padding(12)
        topPanel.BackColor = Color.FromArgb(230, 243, 247)
        Me.Controls.Add(topPanel)

        Dim label As New Label()
        label.Text = "Chọn iProperty hiện có hoặc tạo Custom iProperty mới ngay tại BOM."
        label.AutoSize = True
        label.Location = New Point(12, 10)
        label.Font = New Font("Segoe UI", 9.0F, FontStyle.Bold)
        topPanel.Controls.Add(label)

        Dim searchLabel As New Label()
        searchLabel.Text = "Tìm iProperty:"
        searchLabel.AutoSize = True
        searchLabel.Location = New Point(12, 51)
        topPanel.Controls.Add(searchLabel)

        SearchBox = New TextBox()
        SearchBox.Location = New Point(105, 47)
        SearchBox.Size = New Size(430, 27)
        SearchBox.Anchor = AnchorStyles.Top Or AnchorStyles.Left Or AnchorStyles.Right
        AddHandler SearchBox.TextChanged, AddressOf SearchChanged
        topPanel.Controls.Add(SearchBox)

        Dim clearSearch As New Button()
        clearSearch.Text = "XÓA"
        clearSearch.Size = New Size(62, 28)
        clearSearch.Location = New Point(545, 46)
        clearSearch.Anchor = AnchorStyles.Top Or AnchorStyles.Right
        AddHandler clearSearch.Click, Sub(sender As Object, e As EventArgs) SearchBox.Clear()
        topPanel.Controls.Add(clearSearch)

        CountLabel = New Label()
        CountLabel.AutoSize = True
        CountLabel.ForeColor = Color.DimGray
        CountLabel.Location = New Point(617, 52)
        CountLabel.Anchor = AnchorStyles.Top Or AnchorStyles.Right
        topPanel.Controls.Add(CountLabel)

        Dim customLabel As New Label()
        customLabel.Text = "Custom mới:"
        customLabel.AutoSize = True
        customLabel.Location = New Point(12, 94)
        topPanel.Controls.Add(customLabel)

        CustomNameBox = New TextBox()
        CustomNameBox.Location = New Point(105, 89)
        CustomNameBox.Size = New Size(430, 27)
        CustomNameBox.Anchor = AnchorStyles.Top Or AnchorStyles.Left Or AnchorStyles.Right
        CustomNameBox.Text = ""
        AddHandler CustomNameBox.KeyDown, AddressOf CustomNameKeyDown
        topPanel.Controls.Add(CustomNameBox)

        Dim addCustom As New Button()
        addCustom.Text = "TẠO CUSTOM"
        addCustom.Size = New Size(118, 29)
        addCustom.Location = New Point(545, 88)
        addCustom.Anchor = AnchorStyles.Top Or AnchorStyles.Right
        addCustom.Font = New Font("Segoe UI", 8.5F, FontStyle.Bold)
        AddHandler addCustom.Click, AddressOf AddCustomPropertyClicked
        topPanel.Controls.Add(addCustom)

        PropertyList = New CheckedListBox()
        PropertyList.Dock = DockStyle.Fill
        PropertyList.CheckOnClick = True
        PropertyList.IntegralHeight = False
        PropertyList.BackColor = Color.White
        PropertyList.HorizontalScrollbar = True
        AddHandler PropertyList.ItemCheck, AddressOf PropertyItemCheck
        AddHandler PropertyList.DoubleClick, AddressOf PropertyDoubleClick
        Me.Controls.Add(PropertyList)
        PropertyList.BringToFront()

        Dim bottom As New Panel()
        bottom.Dock = DockStyle.Bottom
        bottom.Height = 60
        bottom.BackColor = Color.FromArgb(230, 243, 247)
        Me.Controls.Add(bottom)

        Dim selectAll As New Button()
        selectAll.Text = "CHỌN ĐANG LỌC"
        selectAll.Size = New Size(132, 34)
        selectAll.Location = New Point(12, 12)
        AddHandler selectAll.Click, AddressOf SelectVisibleClicked
        bottom.Controls.Add(selectAll)

        Dim clearAll As New Button()
        clearAll.Text = "BỎ CHỌN"
        clearAll.Size = New Size(100, 34)
        clearAll.Location = New Point(152, 12)
        AddHandler clearAll.Click, AddressOf ClearCheckedClicked
        bottom.Controls.Add(clearAll)

        Dim okButton As New Button()
        okButton.Text = "THÊM CỘT"
        okButton.Size = New Size(115, 34)
        okButton.Location = New Point(bottom.Width - 250, 12)
        okButton.Anchor = AnchorStyles.Top Or AnchorStyles.Right
        okButton.Font = New Font("Segoe UI", 9.0F, FontStyle.Bold)
        AddHandler okButton.Click, AddressOf OkClicked
        bottom.Controls.Add(okButton)

        Dim cancelButton As New Button()
        cancelButton.Text = "HỦY"
        cancelButton.Size = New Size(90, 34)
        cancelButton.Location = New Point(bottom.Width - 125, 12)
        cancelButton.Anchor = AnchorStyles.Top Or AnchorStyles.Right
        AddHandler cancelButton.Click, AddressOf CancelClicked
        bottom.Controls.Add(cancelButton)

        LoadFilteredProperties("")
    End Sub

    Private Sub LoadFilteredProperties(ByVal filterText As String)
        Dim term As String = If(filterText, "").Trim()
        PropertyList.Items.Clear()
        For Each p As PropertyColumnInfo In AllProperties
            If term.Length > 0 AndAlso p.DisplayText.IndexOf(term, StringComparison.OrdinalIgnoreCase) < 0 Then Continue For
            Dim index As Integer = PropertyList.Items.Add(p, CheckedKeys.Contains(p.Key))
        Next
        CountLabel.Text = PropertyList.Items.Count.ToString() & " mục"
    End Sub

    Private Sub SearchChanged(ByVal sender As Object, ByVal e As EventArgs)
        CaptureChecks()
        LoadFilteredProperties(SearchBox.Text)
    End Sub

    Private Sub PropertyItemCheck(ByVal sender As Object, ByVal e As System.Windows.Forms.ItemCheckEventArgs)
        Dim p As PropertyColumnInfo = TryCast(PropertyList.Items(e.Index), PropertyColumnInfo)
        If p Is Nothing Then Exit Sub
        If e.NewValue = CheckState.Checked Then CheckedKeys.Add(p.Key) Else CheckedKeys.Remove(p.Key)
    End Sub

    Private Sub PropertyDoubleClick(ByVal sender As Object, ByVal e As EventArgs)
        If PropertyList.SelectedIndex < 0 Then Exit Sub
        Dim i As Integer = PropertyList.SelectedIndex
        PropertyList.SetItemChecked(i, Not PropertyList.GetItemChecked(i))
    End Sub

    Private Sub CaptureChecks()
        For i As Integer = 0 To PropertyList.Items.Count - 1
            Dim p As PropertyColumnInfo = TryCast(PropertyList.Items(i), PropertyColumnInfo)
            If p Is Nothing Then Continue For
            If PropertyList.GetItemChecked(i) Then CheckedKeys.Add(p.Key) Else CheckedKeys.Remove(p.Key)
        Next
    End Sub

    Private Sub SelectVisibleClicked(ByVal sender As Object, ByVal e As EventArgs)
        For i As Integer = 0 To PropertyList.Items.Count - 1
            PropertyList.SetItemChecked(i, True)
        Next
    End Sub

    Private Sub ClearCheckedClicked(ByVal sender As Object, ByVal e As EventArgs)
        CheckedKeys.Clear()
        For i As Integer = 0 To PropertyList.Items.Count - 1
            PropertyList.SetItemChecked(i, False)
        Next
    End Sub

    Private Sub CustomNameKeyDown(ByVal sender As Object, ByVal e As System.Windows.Forms.KeyEventArgs)
        If e.KeyCode = Keys.Enter Then
            AddCustomPropertyClicked(sender, EventArgs.Empty)
            e.Handled = True
            e.SuppressKeyPress = True
        End If
    End Sub

    Private Function IsValidCustomPropertyName(ByVal propertyName As String) As Boolean
        If String.IsNullOrWhiteSpace(propertyName) Then Return False
        If propertyName.IndexOf("|"c) >= 0 Then Return False
        If propertyName.IndexOf(ControlChars.Cr) >= 0 OrElse propertyName.IndexOf(ControlChars.Lf) >= 0 OrElse propertyName.IndexOf(ControlChars.Tab) >= 0 Then Return False
        Return True
    End Function

    Private Function BuildVirtualCustomProperty(ByVal propertyName As String) As PropertyColumnInfo
        Dim p As New PropertyColumnInfo()
        p.PropertySetInternalName = "{D5CDD505-2E9C-101B-9397-08002B2CF9AE}"
        p.PropertySetDisplayName = "User Defined Properties"
        p.PropertyName = propertyName.Trim()
        p.Key = BuildPropertyKey(p.PropertySetInternalName, p.PropertyName)
        p.DisplayText = BuildPropertyDisplayText(p.PropertySetDisplayName, p.PropertyName) & "  [NEW CUSTOM]"
        p.DefaultSelected = False
        p.IsVirtualCustom = True
        Return p
    End Function

    Private Sub AddCustomPropertyClicked(ByVal sender As Object, ByVal e As EventArgs)
        Dim raw As String = If(CustomNameBox.Text, "").Trim()
        If raw.Length = 0 Then
            MessageBox.Show("Nhập tên Custom iProperty, ví dụ: POS hoặc PROFILE.", "CUSTOM iPROPERTY", MessageBoxButtons.OK, MessageBoxIcon.Information)
            CustomNameBox.Focus()
            Exit Sub
        End If

        'Cho phép tạo nhiều tên một lần: POS; PROFILE hoặc POS, PROFILE.
        Dim normalized As String = raw.Replace(vbCrLf, ";").Replace(vbCr, ";").Replace(vbLf, ";").Replace(",", ";")
        Dim names() As String = normalized.Split(";"c)
        Dim added As Integer = 0
        Dim duplicateNames As New List(Of String)()
        Dim invalidNames As New List(Of String)()
        CaptureChecks()

        For Each token As String In names
            Dim propertyName As String = If(token, "").Trim()
            If propertyName.Length = 0 Then Continue For
            If Not IsValidCustomPropertyName(propertyName) Then
                invalidNames.Add(propertyName)
                Continue For
            End If
            Dim candidate As PropertyColumnInfo = BuildVirtualCustomProperty(propertyName)
            Dim exists As Boolean = False
            For Each p As PropertyColumnInfo In AllProperties
                If p IsNot Nothing AndAlso String.Equals(p.Key, candidate.Key, StringComparison.OrdinalIgnoreCase) Then
                    exists = True
                    CheckedKeys.Add(p.Key)
                    Exit For
                End If
            Next
            If exists Then
                duplicateNames.Add(propertyName)
            Else
                AllProperties.Add(candidate)
                CheckedKeys.Add(candidate.Key)
                added += 1
            End If
        Next

        AllProperties.Sort(AddressOf ComparePropertyColumns)
        LoadFilteredProperties(SearchBox.Text)
        CustomNameBox.Clear()
        If added > 0 Then
            CountLabel.Text = PropertyList.Items.Count.ToString() & " mục | +" & added.ToString() & " Custom"
        ElseIf invalidNames.Count > 0 Then
            MessageBox.Show("Tên Custom không hợp lệ: " & String.Join(", ", invalidNames.ToArray()) & vbCrLf & "Không dùng ký tự | hoặc xuống dòng/tab trong tên.", "CUSTOM iPROPERTY", MessageBoxButtons.OK, MessageBoxIcon.Warning)
        End If
    End Sub

    Private Sub CancelClicked(ByVal sender As Object, ByVal e As EventArgs)
        Me.DialogResult = DialogResult.Cancel
        Me.Close()
    End Sub

    Private Sub OkClicked(ByVal sender As Object, ByVal e As EventArgs)
        CaptureChecks()
        SelectedProperties.Clear()
        For Each p As PropertyColumnInfo In AllProperties
            If CheckedKeys.Contains(p.Key) Then SelectedProperties.Add(p)
        Next
        If SelectedProperties.Count = 0 Then
            MessageBox.Show("Hãy chọn iProperty hiện có hoặc tạo ít nhất một Custom iProperty mới.", "BOM TOOL PRO", MessageBoxButtons.OK, MessageBoxIcon.Information)
            Exit Sub
        End If
        Me.DialogResult = DialogResult.OK
        Me.Close()
    End Sub
End Class

'====================================================================
' QUẢN LÝ ẨN/HIỆN VÀ THỨ TỰ CỘT - HỖ TRỢ KÉO THẢ
'====================================================================

'####################################################################
' SECTION 17 - COLUMN MANAGER FORM
' Ẩn/hiện, kéo thả, sắp xếp và áp dụng bố cục cột.
'####################################################################

Public Class BomColumnListItem
    Public Column As DataGridViewColumn
    Public Position As Integer

    Public Sub New(ByVal column As DataGridViewColumn, ByVal position As Integer)
        Me.Column = column
        Me.Position = position
    End Sub

    Public Overrides Function ToString() As String
        Dim excelLetter As String = BomColumnManagerForm.ColumnNumberToExcelLetter(Position + 1)
        Return "[" & excelLetter & "]  " & BomColumnManagerForm.GetCleanColumnHeader(Column)
    End Function
End Class

Public Class BomColumnManagerForm
    Inherits Form

    Private _grid As DataGridView
    Private ColumnList As CheckedListBox
    Private DragIndex As Integer = -1
    Private PositionLabel As Label

    Public Sub New(ByVal grid As DataGridView)
        _grid = grid
        BuildInterface()
        LoadColumns()
    End Sub

    Private Sub BuildInterface()
        Me.Text = "QUẢN LÝ CỘT - HIỂN THỊ KÝ TỰ EXCEL"
        Me.StartPosition = FormStartPosition.CenterParent
        Me.Size = New Size(640, 600)
        Me.MinimumSize = New Size(560, 520)
        Me.Font = New Font("Segoe UI", 9.0F)
        Me.BackColor = Color.FromArgb(247, 250, 252)

        Dim label As New Label()
        label.Text = "Ký tự [A], [B], [C]... tương ứng trực tiếp với vị trí cột trên BOM. Tích để hiện cột; kéo thả hoặc dùng LÊN/XUỐNG để đổi thứ tự."
        label.Location = New Point(15, 12)
        label.Size = New Size(595, 42)
        Me.Controls.Add(label)

        PositionLabel = New Label()
        PositionLabel.Text = "CỘT ĐANG CHỌN: -"
        PositionLabel.Font = New Font("Segoe UI", 9.0F, FontStyle.Bold)
        PositionLabel.Location = New Point(15, 55)
        PositionLabel.Size = New Size(595, 24)
        PositionLabel.ForeColor = Color.FromArgb(30, 70, 110)
        Me.Controls.Add(PositionLabel)

        ColumnList = New CheckedListBox()
        ColumnList.Location = New Point(15, 82)
        ColumnList.Size = New Size(470, 420)
        ColumnList.CheckOnClick = True
        ColumnList.IntegralHeight = False
        ColumnList.AllowDrop = True
        ColumnList.BackColor = Color.White
        AddHandler ColumnList.MouseDown, AddressOf ColumnListMouseDown
        AddHandler ColumnList.MouseMove, AddressOf ColumnListMouseMove
        AddHandler ColumnList.DragOver, AddressOf ColumnListDragOver
        AddHandler ColumnList.DragDrop, AddressOf ColumnListDragDrop
        AddHandler ColumnList.SelectedIndexChanged, AddressOf ColumnListSelectedIndexChanged
        Me.Controls.Add(ColumnList)

        Dim upButton As New Button()
        upButton.Text = "LÊN"
        upButton.Location = New Point(500, 105)
        upButton.Size = New Size(110, 36)
        AddHandler upButton.Click, AddressOf MoveUpClicked
        Me.Controls.Add(upButton)

        Dim downButton As New Button()
        downButton.Text = "XUỐNG"
        downButton.Location = New Point(500, 149)
        downButton.Size = New Size(110, 36)
        AddHandler downButton.Click, AddressOf MoveDownClicked
        Me.Controls.Add(downButton)

        Dim topButton As New Button()
        topButton.Text = "LÊN ĐẦU"
        topButton.Location = New Point(500, 205)
        topButton.Size = New Size(110, 36)
        AddHandler topButton.Click, AddressOf MoveTopClicked
        Me.Controls.Add(topButton)

        Dim bottomButton As New Button()
        bottomButton.Text = "XUỐNG CUỐI"
        bottomButton.Location = New Point(500, 249)
        bottomButton.Size = New Size(110, 36)
        AddHandler bottomButton.Click, AddressOf MoveBottomClicked
        Me.Controls.Add(bottomButton)

        Dim allButton As New Button()
        allButton.Text = "HIỆN TẤT CẢ"
        allButton.Location = New Point(500, 315)
        allButton.Size = New Size(110, 40)
        AddHandler allButton.Click, AddressOf ShowAllClicked
        Me.Controls.Add(allButton)

        Dim applyButton As New Button()
        applyButton.Text = "ÁP DỤNG"
        applyButton.Font = New Font("Segoe UI", 9.0F, FontStyle.Bold)
        applyButton.Location = New Point(395, 520)
        applyButton.Size = New Size(105, 38)
        AddHandler applyButton.Click, AddressOf ApplyClicked
        Me.Controls.Add(applyButton)

        Dim closeButton As New Button()
        closeButton.Text = "ĐÓNG"
        closeButton.Location = New Point(510, 520)
        closeButton.Size = New Size(100, 38)
        AddHandler closeButton.Click, AddressOf CloseClicked
        Me.Controls.Add(closeButton)
    End Sub

    Private Sub LoadColumns()
        ColumnList.Items.Clear()
        Dim ordered As New List(Of DataGridViewColumn)()
        For Each col As DataGridViewColumn In _grid.Columns
            ordered.Add(col)
        Next
        ordered.Sort(Function(a As DataGridViewColumn, b As DataGridViewColumn) a.DisplayIndex.CompareTo(b.DisplayIndex))

        For i As Integer = 0 To ordered.Count - 1
            Dim item As New BomColumnListItem(ordered(i), i)
            ColumnList.Items.Add(item, ordered(i).Visible)
        Next

        If ColumnList.Items.Count > 0 Then ColumnList.SelectedIndex = 0
        UpdatePositionLabel()
    End Sub

    Public Shared Function ColumnNumberToExcelLetter(ByVal number As Integer) As String
        If number <= 0 Then Return "?"
        Dim result As String = ""
        Dim value As Integer = number
        While value > 0
            value -= 1
            result = ChrW(65 + (value Mod 26)) & result
            value \= 26
        End While
        Return result
    End Function

    Public Shared Function GetCleanColumnHeader(ByVal column As DataGridViewColumn) As String
        If column Is Nothing Then Return ""
        Dim header As String = Convert.ToString(column.HeaderText)
        If String.IsNullOrWhiteSpace(header) Then header = column.Name
        Dim lines() As String = header.Replace(vbCrLf, vbLf).Replace(vbCr, vbLf).Split(New Char() {ChrW(10)}, StringSplitOptions.RemoveEmptyEntries)
        If lines.Length >= 2 AndAlso IsExcelLetter(lines(0).Trim()) Then
            Return String.Join(" ", lines, 1, lines.Length - 1).Trim()
        End If
        Return header.Replace(vbCrLf, " ").Replace(vbLf, " ").Replace(vbCr, " ").Trim()
    End Function

    Private Shared Function IsExcelLetter(ByVal value As String) As Boolean
        If String.IsNullOrWhiteSpace(value) Then Return False
        For Each ch As Char In value.ToUpperInvariant()
            If ch < "A"c OrElse ch > "Z"c Then Return False
        Next
        Return value.Length <= 4
    End Function

    Private Sub RefreshItemPositions(ByVal selectedIndex As Integer)
        For i As Integer = 0 To ColumnList.Items.Count - 1
            Dim item As BomColumnListItem = TryCast(ColumnList.Items(i), BomColumnListItem)
            If item IsNot Nothing Then item.Position = i
        Next
        ColumnList.Refresh()
        If selectedIndex >= 0 AndAlso selectedIndex < ColumnList.Items.Count Then ColumnList.SelectedIndex = selectedIndex
        UpdatePositionLabel()
    End Sub

    Private Sub UpdatePositionLabel()
        Dim item As BomColumnListItem = TryCast(ColumnList.SelectedItem, BomColumnListItem)
        If item Is Nothing Then
            PositionLabel.Text = "CỘT ĐANG CHỌN: -"
            Exit Sub
        End If
        Dim letter As String = ColumnNumberToExcelLetter(item.Position + 1)
        PositionLabel.Text = "CỘT ĐANG CHỌN: " & letter & "  |  VỊ TRÍ: " & (item.Position + 1).ToString() & "  |  " & GetCleanColumnHeader(item.Column)
    End Sub

    Private Sub ColumnListSelectedIndexChanged(ByVal sender As Object, ByVal e As EventArgs)
        UpdatePositionLabel()
    End Sub

    Private Sub ColumnListMouseDown(ByVal sender As Object, ByVal e As MouseEventArgs)
        DragIndex = ColumnList.IndexFromPoint(e.Location)
        If DragIndex >= 0 Then ColumnList.SelectedIndex = DragIndex
    End Sub

    Private Sub ColumnListMouseMove(ByVal sender As Object, ByVal e As MouseEventArgs)
        If e.Button <> MouseButtons.Left OrElse DragIndex < 0 Then Exit Sub
        ColumnList.DoDragDrop(DragIndex, DragDropEffects.Move)
    End Sub

    Private Sub ColumnListDragOver(ByVal sender As Object, ByVal e As DragEventArgs)
        If e.Data.GetDataPresent(GetType(Integer)) Then e.Effect = DragDropEffects.Move Else e.Effect = DragDropEffects.None
    End Sub

    Private Sub ColumnListDragDrop(ByVal sender As Object, ByVal e As DragEventArgs)
        If Not e.Data.GetDataPresent(GetType(Integer)) Then Exit Sub
        Dim sourceIndex As Integer = CInt(e.Data.GetData(GetType(Integer)))
        Dim clientPoint As Point = ColumnList.PointToClient(New Point(e.X, e.Y))
        Dim targetIndex As Integer = ColumnList.IndexFromPoint(clientPoint)
        If targetIndex < 0 Then targetIndex = ColumnList.Items.Count - 1
        MoveListItem(sourceIndex, targetIndex)
        DragIndex = -1
    End Sub

    Private Sub MoveListItem(ByVal sourceIndex As Integer, ByVal targetIndex As Integer)
        If sourceIndex < 0 OrElse targetIndex < 0 OrElse sourceIndex = targetIndex Then Exit Sub
        Dim value As Object = ColumnList.Items(sourceIndex)
        Dim isChecked As Boolean = ColumnList.GetItemChecked(sourceIndex)
        ColumnList.Items.RemoveAt(sourceIndex)
        If targetIndex > ColumnList.Items.Count Then targetIndex = ColumnList.Items.Count
        ColumnList.Items.Insert(targetIndex, value)
        ColumnList.SetItemChecked(targetIndex, isChecked)
        RefreshItemPositions(targetIndex)
    End Sub

    Private Sub MoveUpClicked(ByVal sender As Object, ByVal e As EventArgs)
        Dim i As Integer = ColumnList.SelectedIndex
        If i <= 0 Then Exit Sub
        MoveListItem(i, i - 1)
    End Sub

    Private Sub MoveDownClicked(ByVal sender As Object, ByVal e As EventArgs)
        Dim i As Integer = ColumnList.SelectedIndex
        If i < 0 OrElse i >= ColumnList.Items.Count - 1 Then Exit Sub
        MoveListItem(i, i + 1)
    End Sub

    Private Sub MoveTopClicked(ByVal sender As Object, ByVal e As EventArgs)
        Dim i As Integer = ColumnList.SelectedIndex
        If i <= 0 Then Exit Sub
        MoveListItem(i, 0)
    End Sub

    Private Sub MoveBottomClicked(ByVal sender As Object, ByVal e As EventArgs)
        Dim i As Integer = ColumnList.SelectedIndex
        If i < 0 OrElse i >= ColumnList.Items.Count - 1 Then Exit Sub
        MoveListItem(i, ColumnList.Items.Count - 1)
    End Sub

    Private Sub ShowAllClicked(ByVal sender As Object, ByVal e As EventArgs)
        For i As Integer = 0 To ColumnList.Items.Count - 1
            ColumnList.SetItemChecked(i, True)
        Next
    End Sub

    Private Sub ApplyClicked(ByVal sender As Object, ByVal e As EventArgs)
        Try
            'Gán DisplayIndex theo đúng thứ tự danh sách. Dùng 2 bước để tránh xung đột DisplayIndex.
            For i As Integer = 0 To ColumnList.Items.Count - 1
                Dim item As BomColumnListItem = TryCast(ColumnList.Items(i), BomColumnListItem)
                If item IsNot Nothing Then item.Column.Visible = ColumnList.GetItemChecked(i)
            Next

            For i As Integer = 0 To ColumnList.Items.Count - 1
                Dim item As BomColumnListItem = TryCast(ColumnList.Items(i), BomColumnListItem)
                If item IsNot Nothing Then item.Column.DisplayIndex = i
            Next

            UpdateGridExcelHeaders()
            Me.DialogResult = DialogResult.OK
            Me.Close()
        Catch ex As Exception
            MessageBox.Show("Không thể áp dụng bố cục cột." & vbCrLf & ex.Message, "BOM TOOL PRO", MessageBoxButtons.OK, MessageBoxIcon.Error)
        End Try
    End Sub

    Private Sub UpdateGridExcelHeaders()
        Dim ordered As New List(Of DataGridViewColumn)()
        For Each col As DataGridViewColumn In _grid.Columns
            ordered.Add(col)
        Next
        ordered.Sort(Function(a As DataGridViewColumn, b As DataGridViewColumn) a.DisplayIndex.CompareTo(b.DisplayIndex))
        For i As Integer = 0 To ordered.Count - 1
            Dim cleanHeader As String = GetCleanColumnHeader(ordered(i))
            ordered(i).HeaderText = ColumnNumberToExcelLetter(i + 1) & vbCrLf & cleanHeader
        Next
        _grid.Invalidate()
    End Sub

    Private Sub CloseClicked(ByVal sender As Object, ByVal e As EventArgs)
        Me.Close()
    End Sub
End Class

'====================================================================
' MÁY TÍNH / THỐNG KÊ IPROPERTY
'====================================================================

'====================================================================
' DASHBOARD - CHỈ DÙNG CACHE RAM
'====================================================================

'####################################################################
' SECTION 18 - DASHBOARD FORM
' Thống kê và tổng quan BOM.
'####################################################################

Public Class BomDashboardForm
    Inherits Form
    Public Sub New(ByVal items As List(Of PartBomItem))
        Me.Text = "BOM DASHBOARD"
        Me.StartPosition = FormStartPosition.CenterParent
        Me.Size = New Size(760, 560)
        Me.Font = New Font("Segoe UI", 9.0F)
        Dim grid As New DataGridView()
        grid.Dock = DockStyle.Fill
        grid.ReadOnly = True
        grid.AllowUserToAddRows = False
        grid.RowHeadersVisible = False
        grid.AutoSizeColumnsMode = DataGridViewAutoSizeColumnsMode.Fill
        grid.Columns.Add("METRIC", "CHỈ SỐ")
        grid.Columns.Add("VALUE", "GIÁ TRỊ")
        Dim totalQty As Integer = 0, purchased As Integer = 0, sheetMetal As Integer = 0
        Dim missingMaterial As Integer = 0, missingDescription As Integer = 0
        Dim totalMass As Double = 0, totalVolume As Double = 0, totalArea As Double = 0
        For Each item As PartBomItem In items
            totalQty += item.Quantity
            If item.IsPurchased Then purchased += 1
            If item.IsSheetMetal Then sheetMetal += 1
            If String.IsNullOrWhiteSpace(item.Material) Then missingMaterial += 1
            If String.IsNullOrWhiteSpace(item.Description) Then missingDescription += 1
            totalMass += item.Mass * item.Quantity
            totalVolume += item.Volume * item.Quantity
            totalArea += item.SurfaceArea * item.Quantity
        Next
        grid.Rows.Add("Unique Part", items.Count)
        grid.Rows.Add("Total Quantity", totalQty)
        grid.Rows.Add("Purchased", purchased)
        grid.Rows.Add("Manufactured", Math.Max(0, items.Count - purchased))
        grid.Rows.Add("Sheet Metal", sheetMetal)
        grid.Rows.Add("Missing Material", missingMaterial)
        grid.Rows.Add("Missing Description", missingDescription)
        grid.Rows.Add("Total Mass (" & BomUnitManager.MassUnit & ")", BomUnitManager.FormatValue(BomUnitManager.ConvertMass(totalMass)))
        grid.Rows.Add("Total Volume (" & BomUnitManager.VolumeUnit & ")", BomUnitManager.FormatValue(BomUnitManager.ConvertVolumeFromCm3(totalVolume)))
        grid.Rows.Add("Total Surface Area (" & BomUnitManager.AreaUnit & ")", BomUnitManager.FormatValue(BomUnitManager.ConvertAreaFromCm2(totalArea)))
        Me.Controls.Add(grid)
    End Sub
End Class

'====================================================================
' PROJECT CHECK - KHÔNG ĐỌC LẠI INVENTOR
'====================================================================

'####################################################################
' SECTION 19 - PROJECT CHECK FORM
' Kiểm tra dữ liệu, duplicate và mở Part từ danh sách lỗi.
'####################################################################

Public Enum BomValidationSeverity
    Critical = 0
    [Error] = 1
    Warning = 2
    Info = 3
End Enum

Public Class BomValidationRule
    Public Id As String = ""
    Public Name As String = ""
    Public Enabled As Boolean = True
    Public Severity As BomValidationSeverity = BomValidationSeverity.Warning
    Public Description As String = ""
    Public CanAutoFix As Boolean = False
End Class

Public Class BomValidationResult
    Public Item As PartBomItem = Nothing
    Public RuleId As String = ""
    Public RuleName As String = ""
    Public Severity As BomValidationSeverity = BomValidationSeverity.Warning
    Public Issue As String = ""
    Public CurrentValue As String = ""
    Public ExpectedValue As String = ""
    Public SuggestedValue As String = ""
    Public CanAutoFix As Boolean = False
    Public FixSafety As String = "REVIEW REQUIRED"
    Public FixPropertyInfo As PropertyColumnInfo = Nothing
    Public Status As String = "OPEN"
End Class

Public Class BomValidationEngine
    Private Const DesignTrackingId As String = "{32853F0F-3444-11D1-9E93-0060B03C1CA6}"

    Public Shared Function Run(ByVal items As List(Of PartBomItem), ByVal drawingStatus As System.Func(Of String, String)) As List(Of BomValidationResult)
        Dim results As New List(Of BomValidationResult)()
        If items Is Nothing Then Return results
        Dim pnMap As New Dictionary(Of String, List(Of PartBomItem))(StringComparer.OrdinalIgnoreCase)
        Dim stockMap As New Dictionary(Of String, List(Of PartBomItem))(StringComparer.OrdinalIgnoreCase)
        For Each item As PartBomItem In items
            If item Is Nothing Then Continue For
            If String.IsNullOrWhiteSpace(item.PartNumber) Then
                Dim expected As String = ""
                Try : expected = IOPath.GetFileNameWithoutExtension(item.FileName) : Catch : End Try
                AddResult(results, item, "CORE.PN.MISSING", "Missing Part Number", BomValidationSeverity.Critical, "Part Number trống", item.PartNumber, expected, expected, expected.Length > 0, "SAFE", MakeProperty("Part Number"))
            Else
                Dim fileBase As String = ""
                Try : fileBase = IOPath.GetFileNameWithoutExtension(item.FileName) : Catch : End Try
                If fileBase.Length > 0 AndAlso Not String.Equals(item.PartNumber.Trim(), fileBase.Trim(), StringComparison.OrdinalIgnoreCase) Then AddResult(results, item, "CONSISTENCY.PN.FILE", "Filename ≠ Part Number", BomValidationSeverity.Warning, "Filename không trùng Part Number", item.PartNumber, fileBase, "", False, "REVIEW REQUIRED", Nothing)
            End If
            If String.IsNullOrWhiteSpace(item.Description) Then AddResult(results, item, "CORE.DESCRIPTION.MISSING", "Missing Description", BomValidationSeverity.Warning, "Description trống", "", "Có Description", "", False, "REVIEW REQUIRED", MakeProperty("Description"))
            If String.IsNullOrWhiteSpace(item.Material) AndAlso Not item.IsPurchased Then AddResult(results, item, "CORE.MATERIAL.MISSING", "Missing Material", BomValidationSeverity.Error, "Material trống", "", "Có Material", "", False, "REVIEW REQUIRED", MakeProperty("Material"))
            If String.IsNullOrWhiteSpace(item.StockNumber) Then AddResult(results, item, "CORE.STOCK.MISSING", "Missing Stock Number", BomValidationSeverity.Info, "Stock Number trống", "", "Có Stock Number", "", False, "REVIEW REQUIRED", MakeProperty("Stock Number"))
            If String.IsNullOrWhiteSpace(item.Revision) Then AddResult(results, item, "CORE.REVISION.MISSING", "Missing Revision", BomValidationSeverity.Info, "Revision trống", "", "Có Revision", "", False, "REVIEW REQUIRED", Nothing)
            If item.IsPurchased AndAlso String.IsNullOrWhiteSpace(item.Vendor) Then AddResult(results, item, "PURCHASED.VENDOR.MISSING", "Missing Vendor", BomValidationSeverity.Warning, "Purchased Part thiếu Vendor", "", "Có Vendor", "", False, "REVIEW REQUIRED", Nothing)
            If item.IsUnsaved Then AddResult(results, item, "FILE.UNSAVED", "Unsaved Document", BomValidationSeverity.Critical, "Document chưa được Save", item.FileName, "Saved file", "", False, "DESTRUCTIVE", Nothing)
            If item.IsReadOnly Then AddResult(results, item, "FILE.READONLY", "Read Only Document", BomValidationSeverity.Info, "Document Read Only", item.FileName, "Writable nếu cần chỉnh sửa", "", False, "REVIEW REQUIRED", Nothing)
            If drawingStatus IsNot Nothing AndAlso Not item.IsUnsaved Then
                Dim ds As String = "UNKNOWN"
                Try : ds = drawingStatus.Invoke(item.FilePath) : Catch : End Try
                If String.Equals(ds, "MISSING", StringComparison.OrdinalIgnoreCase) Then AddResult(results, item, "DRAWING.MISSING", "Missing Drawing", BomValidationSeverity.Warning, "Không tìm thấy Drawing", ds, "OK", "", False, "REVIEW REQUIRED", Nothing)
            End If
            AddIndex(pnMap, item.PartNumber, item)
            AddIndex(stockMap, item.StockNumber, item)
        Next
        AddDuplicateIntelligence(results, pnMap, True)
        AddDuplicateIntelligence(results, stockMap, False)
        AddFormatValidation(results, items)
        AddModelValidation(results, items)
        AddDrawingValidation(results, items, drawingStatus)
        AddGeometryDuplicateIntelligence(results, items)
        Return results
    End Function

    Private Shared Sub AddFormatValidation(ByVal results As List(Of BomValidationResult), ByVal items As List(Of PartBomItem))
        For Each item As PartBomItem In items
            If item Is Nothing Then Continue For
            Dim pn As String = If(item.PartNumber, "").Trim()
            If pn.Length > 0 Then
                If pn.IndexOfAny(New Char() {"/"c, ChrW(92), ":"c, "*"c, "?"c, ChrW(34), "<"c, ">"c, "|"c}) >= 0 Then
                    AddResult(results,item,"FORMAT.PN.INVALID","Invalid Part Number format",BomValidationSeverity.Error,"Part Number chứa ký tự không hợp lệ",pn,"Không chứa ký tự cấm của tên file","",False,"REVIEW REQUIRED",MakeProperty("Part Number"))
                End If
                If Not String.Equals(pn, pn.Trim(), StringComparison.Ordinal) Then
                    AddResult(results,item,"FORMAT.PN.WHITESPACE","Part Number whitespace",BomValidationSeverity.Warning,"Part Number có khoảng trắng thừa",item.PartNumber,pn,pn,True,"SAFE",MakeProperty("Part Number"))
                End If
            End If
            Dim rev As String = If(item.Revision, "").Trim()
            If rev.Length > 0 AndAlso rev.Length > 12 Then
                AddResult(results,item,"FORMAT.REVISION.INVALID","Invalid Revision format",BomValidationSeverity.Warning,"Revision dài bất thường",rev,"<= 12 ký tự","",False,"REVIEW REQUIRED",Nothing)
            End If
            Dim desc As String = If(item.Description, "")
            If desc.Length > 0 AndAlso Not String.Equals(desc, desc.Trim(), StringComparison.Ordinal) Then
                AddResult(results,item,"FORMAT.DESCRIPTION.WHITESPACE","Description whitespace",BomValidationSeverity.Info,"Description có khoảng trắng đầu/cuối",desc,desc.Trim(),desc.Trim(),True,"SAFE",MakeProperty("Description"))
            End If
        Next
    End Sub

    Private Shared Sub AddModelValidation(ByVal results As List(Of BomValidationResult), ByVal items As List(Of PartBomItem))
        For Each item As PartBomItem In items
            If item Is Nothing Then Continue For
            If Not item.IsUnsaved AndAlso Not String.IsNullOrWhiteSpace(item.FilePath) Then
                Try
                    If Not System.IO.File.Exists(item.FilePath) Then AddResult(results,item,"MODEL.FILE.MISSING","Missing model file",BomValidationSeverity.Critical,"File model không tồn tại",item.FilePath,"Existing file","",False,"DESTRUCTIVE",Nothing)
                Catch
                End Try
            End If
            If String.Equals(item.GeometryLoadState,"FAILED",StringComparison.OrdinalIgnoreCase) Then
                AddResult(results,item,"MODEL.GEOMETRY.FAILED","Geometry load failed",BomValidationSeverity.Error,"Không đọc được Geometry",item.GeometryLoadError,"Geometry readable","",False,"REVIEW REQUIRED",Nothing)
            ElseIf String.Equals(item.GeometryLoadState,"LOADED",StringComparison.OrdinalIgnoreCase) Then
                If item.Volume <= 0 Then AddResult(results,item,"MODEL.VOLUME.ZERO","Volume = 0",BomValidationSeverity.Error,"Model có Volume bằng 0",item.Volume.ToString(),"> 0","",False,"REVIEW REQUIRED",Nothing)
                If item.Mass <= 0 AndAlso Not item.IsVirtual Then AddResult(results,item,"MODEL.MASS.ZERO","Mass = 0",BomValidationSeverity.Warning,"Model có Mass bằng 0",item.Mass.ToString(),"> 0","",False,"REVIEW REQUIRED",Nothing)
            End If
            If item.IsReference Then AddResult(results,item,"MODEL.REFERENCE","Reference component",BomValidationSeverity.Info,"Component đang ở BOM Structure Reference",item.BomStructureText,"Intentional Reference","",False,"REVIEW REQUIRED",Nothing)
        Next
    End Sub

    Private Shared Sub AddDrawingValidation(ByVal results As List(Of BomValidationResult), ByVal items As List(Of PartBomItem), ByVal drawingStatus As System.Func(Of String, String))
        If drawingStatus Is Nothing Then Exit Sub
        For Each item As PartBomItem In items
            If item Is Nothing OrElse item.IsUnsaved Then Continue For
            Dim ds As String = "UNKNOWN"
            Try : ds = If(drawingStatus.Invoke(item.FilePath), "UNKNOWN").Trim().ToUpperInvariant() : Catch : ds="UNKNOWN" : End Try
            If ds="SKIPPED" Then Continue For
            If ds="UNKNOWN" Then AddResult(results,item,"DRAWING.UNKNOWN","Drawing status unknown",BomValidationSeverity.Info,"Không xác định được trạng thái Drawing",ds,"OK","",False,"REVIEW REQUIRED",Nothing)
            ' OUTDATED: kiểm tra drawing cùng tên cạnh model, không quét project lần nữa.
            Try
                Dim dir As String=System.IO.Path.GetDirectoryName(item.FilePath)
                Dim baseName As String=System.IO.Path.GetFileNameWithoutExtension(item.FilePath)
                Dim dp As String=""
                Dim idw As String=System.IO.Path.Combine(dir,baseName & ".idw")
                Dim dwg As String=System.IO.Path.Combine(dir,baseName & ".dwg")
                If System.IO.File.Exists(idw) Then
                    dp = idw
                ElseIf System.IO.File.Exists(dwg) Then
                    dp = dwg
                End If
                If dp.Length>0 AndAlso System.IO.File.GetLastWriteTimeUtc(item.FilePath)>System.IO.File.GetLastWriteTimeUtc(dp) Then
                    AddResult(results,item,"DRAWING.OUTDATED","Drawing Outdated",BomValidationSeverity.Warning,"Model mới hơn Drawing",System.IO.File.GetLastWriteTime(item.FilePath).ToString(),"Drawing >= Model","",False,"REVIEW REQUIRED",Nothing)
                End If
            Catch
            End Try
        Next
    End Sub

    Private Shared Sub AddGeometryDuplicateIntelligence(ByVal results As List(Of BomValidationResult), ByVal items As List(Of PartBomItem))
        Dim groups As New Dictionary(Of String,List(Of PartBomItem))(StringComparer.OrdinalIgnoreCase)
        For Each item As PartBomItem In items
            If item Is Nothing OrElse Not String.Equals(item.GeometryLoadState,"LOADED",StringComparison.OrdinalIgnoreCase) OrElse item.Volume<=0 Then Continue For
            Dim key As String=Math.Round(item.Volume,4).ToString("0.####",Globalization.CultureInfo.InvariantCulture) & "|" & Math.Round(item.SurfaceArea,4).ToString("0.####",Globalization.CultureInfo.InvariantCulture) & "|" & Math.Round(item.BoundingMinMm,2).ToString("0.##",Globalization.CultureInfo.InvariantCulture) & "|" & Math.Round(item.BoundingMidMm,2).ToString("0.##",Globalization.CultureInfo.InvariantCulture) & "|" & Math.Round(item.BoundingMaxMm,2).ToString("0.##",Globalization.CultureInfo.InvariantCulture) & "|" & If(item.Material,"").Trim()
            If Not groups.ContainsKey(key) Then groups(key)=New List(Of PartBomItem)()
            groups(key).Add(item)
        Next
        For Each pair As KeyValuePair(Of String,List(Of PartBomItem)) In groups
            If pair.Value.Count<2 Then Continue For
            Dim pn As New HashSet(Of String)(StringComparer.OrdinalIgnoreCase)
            Dim files As New HashSet(Of String)(StringComparer.OrdinalIgnoreCase)
            For Each item As PartBomItem In pair.Value
                pn.Add(If(item.PartNumber, ""))
                files.Add(If(item.FilePath, ""))
            Next
            If files.Count>1 AndAlso pn.Count>1 Then
                For Each item As PartBomItem In pair.Value
                    AddResult(results,item,"DUP.GEOMETRY.CANDIDATE","Possible Geometry Duplicate",BomValidationSeverity.Warning,"Geometry signature giống Part khác",item.PartNumber,"Review duplicate candidate","",False,"REVIEW REQUIRED",Nothing)
                Next
            End If
        Next
    End Sub

    Private Shared Sub AddIndex(ByVal map As Dictionary(Of String, List(Of PartBomItem)), ByVal key As String, ByVal item As PartBomItem)
        If String.IsNullOrWhiteSpace(key) Then Exit Sub
        If Not map.ContainsKey(key.Trim()) Then map(key.Trim()) = New List(Of PartBomItem)()
        map(key.Trim()).Add(item)
    End Sub

    Private Shared Sub AddDuplicateIntelligence(ByVal results As List(Of BomValidationResult), ByVal map As Dictionary(Of String, List(Of PartBomItem)), ByVal isPn As Boolean)
        For Each pair As KeyValuePair(Of String, List(Of PartBomItem)) In map
            If pair.Value.Count < 2 Then Continue For
            Dim files As New HashSet(Of String)(StringComparer.OrdinalIgnoreCase)
            For Each i As PartBomItem In pair.Value
                If i IsNot Nothing Then files.Add(If(i.FilePath, ""))
            Next
            Dim sev As BomValidationSeverity = If(files.Count > 1, BomValidationSeverity.Critical, BomValidationSeverity.Info)
            Dim label As String = If(isPn, If(files.Count > 1, "SAME PN + DIFFERENT FILE", "SAME PN + SAME FILE"), If(files.Count > 1, "SAME STOCK + DIFFERENT FILE", "SAME STOCK + SAME FILE"))
            For Each item As PartBomItem In pair.Value
                AddResult(results, item, If(isPn, "DUP.PN", "DUP.STOCK"), label, sev, label & ": " & pair.Key, pair.Key, "Unique/intentional", "", False, "REVIEW REQUIRED", Nothing)
            Next
        Next
    End Sub

    Private Shared Function MakeProperty(ByVal name As String) As PropertyColumnInfo
        Dim p As New PropertyColumnInfo()
        p.PropertyName = name : p.PropertySetInternalName = DesignTrackingId : p.PropertySetDisplayName = "Design Tracking Properties"
        p.Key = DesignTrackingId & "|" & name : p.DisplayText = name
        Return p
    End Function

    Private Shared Sub AddResult(ByVal list As List(Of BomValidationResult), ByVal item As PartBomItem, ByVal id As String, ByVal ruleName As String, ByVal severity As BomValidationSeverity, ByVal issue As String, ByVal currentValue As String, ByVal expected As String, ByVal suggested As String, ByVal canFix As Boolean, ByVal safety As String, ByVal p As PropertyColumnInfo)
        Dim r As New BomValidationResult()
        r.Item=item : r.RuleId=id : r.RuleName=ruleName : r.Severity=severity : r.Issue=issue : r.CurrentValue=If(currentValue,"") : r.ExpectedValue=If(expected,"") : r.SuggestedValue=If(suggested,"") : r.CanAutoFix=canFix : r.FixSafety=safety : r.FixPropertyInfo=p
        list.Add(r)
    End Sub
End Class

Public Class BomProjectCheckForm
    Inherits Form
    Private _items As List(Of PartBomItem)
    Private _openPartCallback As System.Action(Of PartBomItem)
    Private _drawingStatus As System.Func(Of String, String)
    Private _stageFix As System.Action(Of BomValidationResult)
    Private _grid As DataGridView
    Private _results As New List(Of BomValidationResult)()
    Private _filter As ComboBox
    Private _summary As Label

    Public Sub New(ByVal items As List(Of PartBomItem), ByVal openPartCallback As System.Action(Of PartBomItem), ByVal drawingStatus As System.Func(Of String, String), ByVal stageFix As System.Action(Of BomValidationResult))
        _items=If(items, New List(Of PartBomItem)()) : _openPartCallback=openPartCallback : _drawingStatus=drawingStatus : _stageFix=stageFix
        Me.Text="VALIDATION ENGINE 2.0" : Me.StartPosition=FormStartPosition.CenterParent : Me.Size=New Size(1320,720) : Me.Font=New Font("Segoe UI",9.0F)
        Dim top As New FlowLayoutPanel() : top.Dock=DockStyle.Top : top.Height=48 : top.Padding=New Padding(8)
        Dim runBtn As New Button() : runBtn.Text="RUN VALIDATION" : runBtn.Width=130 : AddHandler runBtn.Click, AddressOf RunClicked : top.Controls.Add(runBtn)
        _filter=New ComboBox() : _filter.DropDownStyle=ComboBoxStyle.DropDownList : _filter.Width=130 : _filter.Items.AddRange(New Object(){"ALL","CRITICAL","ERROR","WARNING","INFO"}) : _filter.SelectedIndex=0 : AddHandler _filter.SelectedIndexChanged, AddressOf FilterChanged : top.Controls.Add(_filter)
        Dim fixBtn As New Button() : fixBtn.Text="FIX ALL SAFE" : fixBtn.Width=120 : AddHandler fixBtn.Click, AddressOf FixAllSafeClicked : top.Controls.Add(fixBtn)
        Dim fixSelectedBtn As New Button() : fixSelectedBtn.Text="FIX SELECTED SAFE" : fixSelectedBtn.Width=140 : AddHandler fixSelectedBtn.Click, AddressOf FixSelectedSafeClicked : top.Controls.Add(fixSelectedBtn)
        _summary=New Label() : _summary.AutoSize=True : _summary.Padding=New Padding(12,7,0,0) : top.Controls.Add(_summary)
        _grid=New DataGridView() : _grid.Dock=DockStyle.Fill : _grid.ReadOnly=True : _grid.AllowUserToAddRows=False : _grid.RowHeadersVisible=False : _grid.SelectionMode=DataGridViewSelectionMode.FullRowSelect : _grid.AutoSizeColumnsMode=DataGridViewAutoSizeColumnsMode.None
        AddCol("SEVERITY","STATUS",85) : AddCol("PART","PART NUMBER",130) : AddCol("FILE","FILE",180) : AddCol("RULE","RULE",190) : AddCol("ISSUE","ISSUE",260) : AddCol("CURRENT","CURRENT",140) : AddCol("EXPECTED","EXPECTED",140) : AddCol("FIX","FIX",150) : AddCol("STATE","STATE",85)
        AddHandler _grid.CellDoubleClick, AddressOf GridDoubleClicked
        Me.Controls.Add(_grid) : Me.Controls.Add(top)
        RunValidation()
    End Sub
    Private Sub AddCol(ByVal n As String, ByVal h As String, ByVal w As Integer)
        Dim c As New DataGridViewTextBoxColumn() : c.Name=n : c.HeaderText=h : c.Width=w : _grid.Columns.Add(c)
    End Sub
    Private Sub RunClicked(ByVal s As Object, ByVal e As EventArgs)
        RunValidation()
    End Sub
    Private Sub RunValidation()
        Me.Cursor=Cursors.WaitCursor
        Try
            _results = BomValidationEngine.Run(_items, _drawingStatus)
            LoadRows()
        Finally
            Me.Cursor = Cursors.Default
        End Try
    End Sub
    Private Sub FilterChanged(ByVal s As Object, ByVal e As EventArgs)
        LoadRows()
    End Sub
    Private Sub LoadRows()
        _grid.Rows.Clear()
        Dim f As String=If(_filter Is Nothing OrElse _filter.SelectedItem Is Nothing,"ALL",Convert.ToString(_filter.SelectedItem))
        Dim c0 As Integer=0,c1 As Integer=0,c2 As Integer=0,c3 As Integer=0
        For Each r As BomValidationResult In _results
            Select Case r.Severity
                Case BomValidationSeverity.Critical
                    c0 += 1
                Case BomValidationSeverity.Error
                    c1 += 1
                Case BomValidationSeverity.Warning
                    c2 += 1
                Case Else
                    c3 += 1
            End Select
            Dim sev As String=r.Severity.ToString().ToUpperInvariant()
            If f<>"ALL" AndAlso f<>sev Then Continue For
            Dim fixText As String=If(r.CanAutoFix, r.FixSafety & ": " & r.SuggestedValue, "-")
            Dim idx As Integer=_grid.Rows.Add(sev,r.Item.PartNumber,r.Item.FileName,r.RuleName,r.Issue,r.CurrentValue,r.ExpectedValue,fixText,r.Status) : _grid.Rows(idx).Tag=r
        Next
        _summary.Text = "CRITICAL " & c0.ToString() &
                        "   ERROR " & c1.ToString() &
                        "   WARNING " & c2.ToString() &
                        "   INFO " & c3.ToString() &
                        "   | TOTAL " & _results.Count.ToString()
    End Sub
    Private Sub FixAllSafeClicked(ByVal s As Object, ByVal e As EventArgs)
        Dim staged As Integer=0
        For Each r As BomValidationResult In _results
            If r.CanAutoFix AndAlso String.Equals(r.FixSafety,"SAFE",StringComparison.OrdinalIgnoreCase) AndAlso r.Status="OPEN" Then
                If _stageFix IsNot Nothing Then _stageFix.Invoke(r) : staged+=1
            End If
        Next
        LoadRows()
        MessageBox.Show(staged.ToString() & " SAFE fix đã được STAGE. Inventor CHƯA bị ghi. Dùng REVIEW / COMMIT ở cửa sổ BOM chính.","VALIDATION ENGINE",MessageBoxButtons.OK,MessageBoxIcon.Information)
    End Sub
    Private Sub FixSelectedSafeClicked(ByVal s As Object, ByVal e As EventArgs)
        Dim staged As Integer=0
        For Each row As DataGridViewRow In _grid.SelectedRows
            Dim r As BomValidationResult=TryCast(row.Tag,BomValidationResult)
            If r Is Nothing Then Continue For
            If r.CanAutoFix AndAlso String.Equals(r.FixSafety,"SAFE",StringComparison.OrdinalIgnoreCase) AndAlso r.Status="OPEN" Then
                If _stageFix IsNot Nothing Then _stageFix.Invoke(r) : staged+=1
            End If
        Next
        LoadRows()
        MessageBox.Show(staged.ToString() & " SAFE fix đã được STAGE từ các dòng chọn. Dùng REVIEW / COMMIT ở BOM chính.","VALIDATION ENGINE",MessageBoxButtons.OK,MessageBoxIcon.Information)
    End Sub
    Private Sub GridDoubleClicked(ByVal s As Object, ByVal e As DataGridViewCellEventArgs)
        If e.RowIndex<0 Then Exit Sub
        Dim r As BomValidationResult=TryCast(_grid.Rows(e.RowIndex).Tag,BomValidationResult)
        If r IsNot Nothing AndAlso r.Item IsNot Nothing AndAlso _openPartCallback IsNot Nothing Then _openPartCallback.Invoke(r.Item)
    End Sub
End Class


'####################################################################
' SECTION 20 - CALCULATOR / ANALYTICS FORM
' Tính tổng, trung bình, min/max và phân tích theo phạm vi dữ liệu.
'####################################################################

Public Class BomCalculatorForm
    Inherits Form

    Private AllItems As List(Of PartBomItem)
    Private FilteredItems As List(Of PartBomItem)
    Private SelectedItems As List(Of PartBomItem)
    Private AssemblyItems As List(Of PartBomItem)
    Private Properties As List(Of PropertyColumnInfo)
    Private ScopeCombo As ComboBox
    Private PropertyCombo As ComboBox
    Private OperationCombo As ComboBox
    Private SearchBox As TextBox
    Private ResultBox As TextBox
    Private PropertyOptions As New List(Of Object)()

    Public Sub New(ByVal allRows As List(Of PartBomItem), ByVal filteredRows As List(Of PartBomItem), ByVal selectedRows As List(Of PartBomItem), ByVal assemblyRows As List(Of PartBomItem), ByVal properties As List(Of PropertyColumnInfo))
        AllItems = If(allRows, New List(Of PartBomItem)())
        FilteredItems = If(filteredRows, New List(Of PartBomItem)())
        SelectedItems = If(selectedRows, New List(Of PartBomItem)())
        AssemblyItems = If(assemblyRows, New List(Of PartBomItem)())
        Properties = If(properties, New List(Of PropertyColumnInfo)())
        BuildInterface()
        LoadPropertyOptions("")
    End Sub

    Private Sub BuildInterface()
        Me.Text = "MÁY TÍNH & THỐNG KÊ BOM"
        Me.StartPosition = FormStartPosition.CenterParent
        Me.Size = New Size(760, 650)
        Me.MinimumSize = New Size(680, 560)
        Me.Font = New Font("Segoe UI", 9.0F)
        Me.BackColor = Color.FromArgb(246, 250, 252)

        Dim title As New Label()
        title.Text = "TÍNH TOÁN / THỐNG KÊ iPROPERTY"
        title.Font = New Font("Segoe UI", 14.0F, FontStyle.Bold)
        title.ForeColor = Color.FromArgb(35, 110, 130)
        title.Location = New Point(20, 16)
        title.AutoSize = True
        Me.Controls.Add(title)

        AddLabel("Phạm vi:", 22, 68)
        ScopeCombo = New ComboBox()
        ScopeCombo.DropDownStyle = ComboBoxStyle.DropDownList
        ScopeCombo.Location = New Point(145, 64)
        ScopeCombo.Size = New Size(280, 28)
        ScopeCombo.Items.AddRange(New Object() {"Toàn bộ BOM", "Các dòng đang lọc", "Các dòng đang chọn", "Assembly đang chọn"})
        ScopeCombo.SelectedIndex = 0
        Me.Controls.Add(ScopeCombo)

        AddLabel("Tìm iProperty:", 22, 108)
        SearchBox = New TextBox()
        SearchBox.Location = New Point(145, 104)
        SearchBox.Size = New Size(280, 27)
        AddHandler SearchBox.TextChanged, AddressOf SearchChanged
        Me.Controls.Add(SearchBox)

        AddLabel("iProperty:", 22, 148)
        PropertyCombo = New ComboBox()
        PropertyCombo.DropDownStyle = ComboBoxStyle.DropDownList
        PropertyCombo.Location = New Point(145, 144)
        PropertyCombo.Size = New Size(480, 28)
        Me.Controls.Add(PropertyCombo)

        AddLabel("Phép tính:", 22, 188)
        OperationCombo = New ComboBox()
        OperationCombo.DropDownStyle = ComboBoxStyle.DropDownList
        OperationCombo.Location = New Point(145, 184)
        OperationCombo.Size = New Size(280, 28)
        OperationCombo.Items.AddRange(New Object() {"Tổng", "Tổng × QTY", "Trung bình", "Nhỏ nhất", "Lớn nhất", "Đếm dòng có dữ liệu", "Thống kê theo giá trị"})
        OperationCombo.SelectedIndex = 0
        Me.Controls.Add(OperationCombo)

        Dim calcButton As New Button()
        calcButton.Text = "TÍNH"
        calcButton.Font = New Font("Segoe UI", 9.5F, FontStyle.Bold)
        calcButton.BackColor = Color.FromArgb(211, 240, 245)
        calcButton.Location = New Point(445, 182)
        calcButton.Size = New Size(90, 34)
        AddHandler calcButton.Click, AddressOf CalculateClicked
        Me.Controls.Add(calcButton)

        Dim copyButton As New Button()
        copyButton.Text = "COPY"
        copyButton.Location = New Point(545, 182)
        copyButton.Size = New Size(80, 34)
        AddHandler copyButton.Click, AddressOf CopyClicked
        Me.Controls.Add(copyButton)

        ResultBox = New TextBox()
        ResultBox.Location = New Point(22, 235)
        ResultBox.Size = New Size(700, 340)
        ResultBox.Multiline = True
        ResultBox.ScrollBars = ScrollBars.Both
        ResultBox.ReadOnly = True
        ResultBox.Font = New Font("Consolas", 10.0F)
        ResultBox.BackColor = Color.White
        ResultBox.Anchor = AnchorStyles.Top Or AnchorStyles.Bottom Or AnchorStyles.Left Or AnchorStyles.Right
        Me.Controls.Add(ResultBox)

        Dim closeButton As New Button()
        closeButton.Text = "ĐÓNG"
        closeButton.Location = New Point(632, 587)
        closeButton.Size = New Size(90, 34)
        closeButton.Anchor = AnchorStyles.Bottom Or AnchorStyles.Right
        AddHandler closeButton.Click, Sub(sender As Object, e As EventArgs) Me.Close()
        Me.Controls.Add(closeButton)
    End Sub

    Private Sub AddLabel(ByVal text As String, ByVal x As Integer, ByVal y As Integer)
        Dim l As New Label()
        l.Text = text
        l.Location = New Point(x, y)
        l.AutoSize = True
        Me.Controls.Add(l)
    End Sub

    Private Sub SearchChanged(ByVal sender As Object, ByVal e As EventArgs)
        LoadPropertyOptions(SearchBox.Text)
    End Sub

    Private Sub LoadPropertyOptions(ByVal filter As String)
        PropertyCombo.Items.Clear()
        PropertyOptions.Clear()
        AddOption("QTY", Nothing, filter)
        For Each p As PropertyColumnInfo In Properties
            AddOption(p.PropertyName & " [" & p.PropertySetDisplayName & "]", p, filter)
        Next
        If PropertyCombo.Items.Count > 0 Then PropertyCombo.SelectedIndex = 0
    End Sub

    Private Sub AddOption(ByVal caption As String, ByVal value As Object, ByVal filter As String)
        If filter IsNot Nothing AndAlso filter.Trim().Length > 0 AndAlso caption.IndexOf(filter.Trim(), StringComparison.OrdinalIgnoreCase) < 0 Then Exit Sub
        PropertyCombo.Items.Add(caption)
        PropertyOptions.Add(value)
    End Sub

    Private Function GetScopeItems() As List(Of PartBomItem)
        Select Case ScopeCombo.SelectedIndex
            Case 1 : Return FilteredItems
            Case 2 : Return SelectedItems
            Case 3 : Return AssemblyItems
            Case Else : Return AllItems
        End Select
    End Function

    Private Function GetValue(ByVal item As PartBomItem, ByVal propertyOption As Object) As String
        If item Is Nothing Then Return ""
        If propertyOption Is Nothing Then Return item.Quantity.ToString()
        Dim p As PropertyColumnInfo = TryCast(propertyOption, PropertyColumnInfo)
        If p Is Nothing Then Return ""
        If item.SelectedPropertyValues.ContainsKey(p.Key) Then Return Convert.ToString(item.SelectedPropertyValues(p.Key))
        Return ""
    End Function

    Private Function TryNumber(ByVal text As String, ByRef value As Double) As Boolean
        Dim cleaned As String = If(text, "").Trim().Replace(" ", "")
        If Double.TryParse(cleaned, Globalization.NumberStyles.Any, Globalization.CultureInfo.CurrentCulture, value) Then Return True
        If Double.TryParse(cleaned.Replace(",", "."), Globalization.NumberStyles.Any, Globalization.CultureInfo.InvariantCulture, value) Then Return True
        Return False
    End Function

    Private Function SumNumbers(ByVal values As List(Of Double)) As Double
        Dim result As Double = 0
        For Each value As Double In values
            result += value
        Next
        Return result
    End Function

    Private Function AverageNumbers(ByVal values As List(Of Double)) As Double
        If values Is Nothing OrElse values.Count = 0 Then Return 0
        Return SumNumbers(values) / CDbl(values.Count)
    End Function

    Private Function MinimumNumber(ByVal values As List(Of Double)) As Double
        If values Is Nothing OrElse values.Count = 0 Then Return 0
        Dim result As Double = values(0)
        For Each value As Double In values
            If value < result Then result = value
        Next
        Return result
    End Function

    Private Function MaximumNumber(ByVal values As List(Of Double)) As Double
        If values Is Nothing OrElse values.Count = 0 Then Return 0
        Dim result As Double = values(0)
        For Each value As Double In values
            If value > result Then result = value
        Next
        Return result
    End Function

    Private Function SumIntegerValues(ByVal values As SortedDictionary(Of String, Integer)) As Integer
        Dim result As Integer = 0
        For Each pair As KeyValuePair(Of String, Integer) In values
            result += pair.Value
        Next
        Return result
    End Function

    Private Sub CalculateClicked(ByVal sender As Object, ByVal e As EventArgs)
        If PropertyCombo.SelectedIndex < 0 Then Exit Sub
        Dim rows As List(Of PartBomItem) = GetScopeItems()
        Dim propertyOption As Object = PropertyOptions(PropertyCombo.SelectedIndex)
        Dim propertyCaption As String = Convert.ToString(PropertyCombo.SelectedItem)
        Dim operation As String = Convert.ToString(OperationCombo.SelectedItem)
        Dim numbers As New List(Of Double)()
        Dim weightedSum As Double = 0
        Dim groups As New SortedDictionary(Of String, Integer)(StringComparer.OrdinalIgnoreCase)

        For Each item As PartBomItem In rows
            Dim raw As String = GetValue(item, propertyOption)
            If raw.Trim().Length > 0 Then
                If Not groups.ContainsKey(raw) Then groups(raw) = 0
                groups(raw) += Math.Max(1, item.Quantity)
            End If
            Dim number As Double = 0
            If TryNumber(raw, number) Then
                numbers.Add(number)
                weightedSum += number * Math.Max(1, item.Quantity)
            End If
        Next

        Dim sb As New System.Text.StringBuilder()
        sb.AppendLine("BOM TOOL PRO V9 - CALCULATION")
        sb.AppendLine("Phạm vi: " & Convert.ToString(ScopeCombo.SelectedItem))
        sb.AppendLine("iProperty: " & propertyCaption)
        sb.AppendLine("Phép tính: " & operation)
        sb.AppendLine(New String("-"c, 56))

        If operation = "Thống kê theo giá trị" Then
            For Each pair As KeyValuePair(Of String, Integer) In groups
                sb.AppendLine(pair.Key.PadRight(38) & pair.Value.ToString().PadLeft(10))
            Next
            sb.AppendLine(New String("-"c, 56))
            sb.AppendLine("Số nhóm: " & groups.Count.ToString())
        ElseIf operation = "Đếm dòng có dữ liệu" Then
            sb.AppendLine("Kết quả: " & SumIntegerValues(groups).ToString())
        ElseIf numbers.Count = 0 Then
            sb.AppendLine("Không có dữ liệu số hợp lệ trong phạm vi đã chọn.")
        Else
            Dim result As Double = 0
            Select Case operation
                Case "Tổng × QTY" : result = weightedSum
                Case "Trung bình" : result = AverageNumbers(numbers)
                Case "Nhỏ nhất" : result = MinimumNumber(numbers)
                Case "Lớn nhất" : result = MaximumNumber(numbers)
                Case Else : result = SumNumbers(numbers)
            End Select
            sb.AppendLine("Kết quả: " & result.ToString("0.####"))
            sb.AppendLine("Số dòng số hợp lệ: " & numbers.Count.ToString())
            sb.AppendLine("Tổng có nhân QTY: " & weightedSum.ToString("0.####"))
        End If
        ResultBox.Text = sb.ToString()
    End Sub

    Private Sub CopyClicked(ByVal sender As Object, ByVal e As EventArgs)
        If ResultBox.Text.Length > 0 Then Clipboard.SetText(ResultBox.Text)
    End Sub
End Class

'####################################################################
' END OF BOM TOOL PRO V17 - SCIENTIFIC STRUCTURE
'####################################################################

'
' ============================================================================
' EMBEDDED SOURCE MODULE: balloon-update Beta
' Disabled reference source retained inside MASTER for controlled integration.
' ============================================================================
'SRC> '##########################
'SRC> '###   Balloon Update   ###
'SRC> '##########################
'SRC> 
'SRC> Sub Main()
'SRC> 
'SRC> 	Dim doc As Inventor.Document = ThisDoc.Document
'SRC> 	Guard.OnlyDrawingDocuments(doc, "This tool is not compatible with this type of file.  Please run from a drawing.")
'SRC> 	FixItemNumbers
'SRC> 
'SRC> End Sub 'Main()'
'SRC> 
'SRC> Sub FixItemNumbers()
'SRC> 
'SRC> 	Dim doc As Inventor.DrawingDocument = ThisDoc.Document
'SRC> 	Dim drawingBoms As Inventor.DrawingBOMs = doc.DrawingBOMs
'SRC> 	Dim drawingBom As Inventor.DrawingBOM
'SRC> 	Dim drawingBomRow As DrawingBOMRow
'SRC> 	Dim bomRow As Inventor.BOMRow
'SRC> 	Dim stockNumber As String
'SRC> 	
'SRC> 	For Each drawingBom In drawingBoms
'SRC> 
'SRC> 		For Each drawingBomRow In drawingBom.DrawingBOMRows
'SRC> 			
'SRC> 			bomRow = drawingBomRow.BOMRow
'SRC> 			stockNumber = GetStockNumber(bomRow)
'SRC> 			Try
'SRC> 				If (IsFabricatedPart(stockNumber)) Then
'SRC> 					bomRow.ItemNumber = GetSheetView(bomRow)
'SRC> 				End If
'SRC> 			Catch
'SRC> 			End Try
'SRC> 		Next
'SRC> 	Next
'SRC> 	
'SRC> End Sub
'SRC> 
'SRC> 
'SRC> Public Function GetStockNumber(ByRef bomRow As Inventor.BOMRow)
'SRC> 
'SRC> 	Dim doc As Inventor.Document = bomRow.ComponentDefinitions(1).Document
'SRC> 	Return PropertyShim.GetProperty(doc, "Stock Number")
'SRC> 
'SRC> End Function
'SRC> 
'SRC> Public Function GetSheetView(ByRef BOMRow As Inventor.BOMRow)
'SRC> 
'SRC> 	Dim doc As Inventor.Document = BOMRow.ComponentDefinitions(1).Document
'SRC> 	Return PropertyShim.GetProperty(doc, "Sheet") & PropertyShim.GetProperty(doc, "View")
'SRC> 
'SRC> End Function
'SRC> 
'SRC> 
'SRC> Public Function IsFabricatedPart(ByRef input As String) As Boolean
'SRC>         Return Text.RegularExpressions.Regex.IsMatch(If(input,"error"), "\b\d{3,4}\-[0123456789]\d\d[a-z|A-Z]*\b")
'SRC> End Function
'SRC> 
'SRC> 
'SRC> Public Class Guard
'SRC> 
'SRC>     Shared Sub OnlyDrawingDocuments(doc As Inventor.Document, message As String)
'SRC>         Dim tempDocument As Inventor.DrawingDocument
'SRC>         Try
'SRC>             tempDocument = doc
'SRC>         Catch ex As Exception
'SRC>             Throw New SystemException(message)
'SRC>         End Try
'SRC>     End Sub
'SRC> 
'SRC> End Class
'SRC> 
'SRC> 
'SRC> Public Class PropertyShim
'SRC> 
'SRC>         Shared ReadOnly PropertyLookup As Dictionary(Of String, String) = New Dictionary(Of String,String)(StringComparer.OrdinalIgnoreCase) From 
'SRC>         {{"Title", "Inventor Summary Information"},
'SRC>         {"Subject", "Inventor Summary Information"},
'SRC>         {"Author", "Inventor Summary Information"},
'SRC>         {"Keywords", "Inventor Summary Information"},
'SRC>         {"Comments", "Inventor Summary Information"},
'SRC>         {"Last Saved By", "Inventor Summary Information"},
'SRC>         {"Revision Number", "Inventor Summary Information"},
'SRC>         {"Thumbnail", "Inventor Summary Information"},
'SRC>         {"Category","Inventor Document Summary Information"},
'SRC>         {"Manager","Inventor Document Summary Information"},
'SRC>         {"Company","Inventor Document Summary Information"},
'SRC>         {"Creation Time","Design Tracking Properties"},
'SRC>         {"Part Number","Design Tracking Properties"},
'SRC>         {"Project","Design Tracking Properties"},
'SRC>         {"Cost Center","Design Tracking Properties"},
'SRC>         {"Checked By","Design Tracking Properties"},
'SRC>         {"Date Checked","Design Tracking Properties"},
'SRC>         {"Engr Approved By","Design Tracking Properties"},
'SRC>         {"Engr Date Approved","Design Tracking Properties"},
'SRC>         {"User Status","Design Tracking Properties"},
'SRC>         {"Material","Design Tracking Properties"},
'SRC>         {"Part Property Revision Id","Design Tracking Properties"},
'SRC>         {"Catalog Web Link","Design Tracking Properties"},
'SRC>         {"Part Icon","Design Tracking Properties"},
'SRC>         {"Description","Design Tracking Properties"},
'SRC>         {"Vendor","Design Tracking Properties"},
'SRC>         {"Document SubType","Design Tracking Properties"},
'SRC>         {"Document SubType Name","Design Tracking Properties"},
'SRC>         {"Proxy Refresh Date","Design Tracking Properties"},
'SRC>         {"Mfg Approved By","Design Tracking Properties"},
'SRC>         {"Mfg Date Approved","Design Tracking Properties"},
'SRC>         {"Cost","Design Tracking Properties"},
'SRC>         {"Standard","Design Tracking Properties"},
'SRC>         {"Design Status","Design Tracking Properties"},
'SRC>         {"Designer","Design Tracking Properties"},
'SRC>         {"Engineer","Design Tracking Properties"},
'SRC>         {"Authority","Design Tracking Properties"},
'SRC>         {"Parameterized Template","Design Tracking Properties"},
'SRC>         {"Template Row","Design Tracking Properties"},
'SRC>         {"External Property Revision Id","Design Tracking Properties"},
'SRC>         {"Standard Revision","Design Tracking Properties"},
'SRC>         {"Manufacturer","Design Tracking Properties"},
'SRC>         {"Standards Organization","Design Tracking Properties"},
'SRC>         {"Language","Design Tracking Properties"},
'SRC>         {"Defer Updates","Design Tracking Properties"},
'SRC>         {"Size Designation","Design Tracking Properties"},
'SRC>         {"Categories","Design Tracking Properties"},
'SRC>         {"Stock Number","Design Tracking Properties"},
'SRC>         {"Weld Material","Design Tracking Properties"},
'SRC>         {"Mass","Design Tracking Properties"},
'SRC>         {"SurfaceArea","Design Tracking Properties"},
'SRC>         {"Volume","Design Tracking Properties"},
'SRC>         {"Density","Design Tracking Properties"},
'SRC>         {"Valid MassProps","Design Tracking Properties"},
'SRC>         {"Flat Pattern Width","Design Tracking Properties"},
'SRC>         {"Flat Pattern Length","Design Tracking Properties"},
'SRC>         {"Flat Pattern Area","Design Tracking Properties"},
'SRC>         {"Sheet Metal Rule","Design Tracking Properties"},
'SRC>         {"Last Updated With","Design Tracking Properties"},
'SRC>         {"Sheet Metal Width","Design Tracking Properties"},
'SRC>         {"Sheet Metal Length","Design Tracking Properties"},
'SRC>         {"Sheet Metal Area","Design Tracking Properties"},
'SRC>         {"Material Identifier","Design Tracking Properties"},
'SRC>         {"Appearance","Design Tracking Properties"},
'SRC>         {"Flat Pattern Defer Update","Design Tracking Properties"}}
'SRC> 
'SRC>         Public Shared PropertySetLookup As HashSet(Of String) = New HashSet(Of String) From {
'SRC>             "Inventor Summary Information",
'SRC>             "Inventor Document Summary Information",
'SRC>             "Design Tracking Properties",
'SRC>             "Inventor User Defined Properties"
'SRC>         }
'SRC> 
'SRC>         ''' <summary>
'SRC>         ''' Return the specified document property's value. This is the short form of this function.
'SRC>         ''' Only requires a document and property propertyName. 
'SRC>         ''' </summary>
'SRC>         ''' <param name="doc">Inventor Document</param>
'SRC>         ''' <param name="propertyName">Name of the Property</param>
'SRC>         ''' <returns></returns>
'SRC>         Shared Function GetProperty(ByRef doc As Inventor.Document, ByVal propertyName As String) As Object
'SRC> 
'SRC>             Dim setName As String
'SRC>             Dim documentPropertySets As Inventor.PropertySets = doc.PropertySets
'SRC>             'Get propertySet for provided propertyName (if exists)
'SRC>             If PropertyLookup.TryGetValue(propertyName, setName) Then
'SRC>                 Return documentPropertySets.Item(setName).Item(propertyName).Value
'SRC>             End If
'SRC> 
'SRC>             'Not found in standard properties, search custom properties
'SRC>             Dim currentPropertySet As Inventor.PropertySet = documentPropertySets.Item("Inventor User Defined Properties")
'SRC>             Try
'SRC>                 Return currentPropertySet.Item(propertyName).Value
'SRC>             Catch
'SRC>             End Try
'SRC> 
'SRC>             'Still not found, search other custom property sets!
'SRC>             If documentPropertySets.Count >= PropertySetLookup.Count Then
'SRC>                 For Each currentPropertySet In doc.PropertySets
'SRC>                     If PropertySetLookup.Contains(currentPropertySet.DisplayName)
'SRC>                         Return ""
'SRC>                     End If
'SRC> 
'SRC>                     Try
'SRC>                         Return currentPropertySet.Item(propertyName).Value
'SRC>                     Catch ex As Exception
'SRC>                         Return ""
'SRC>                     End Try
'SRC>                 Next
'SRC>             End If
'SRC> 
'SRC>             'Still not found, return nothing...
'SRC>             Return ""
'SRC> 
'SRC>         End Function
'SRC> 
'SRC>         Shared Function GetProperty(ByRef doc As Inventor.Document, ByVal setName As String, ByVal propertyName As String) As Object
'SRC> 
'SRC>             Dim documentPropertySets As Inventor.PropertySets = doc.PropertySets
'SRC>             Try
'SRC>                 Dim currentPropertySet As Inventor.PropertySet = documentPropertySets.Item(setName)
'SRC>                 Dim currentProperty As Inventor.Property = currentPropertySet.Item(propertyName)
'SRC>                 Return currentProperty.Value
'SRC>             Catch ex As Exception
'SRC>                 Return ""
'SRC>             End Try
'SRC> 
'SRC>         End Function
'SRC>     Shared Sub SetProperty(ByRef doc As Inventor.Document, ByVal propertyName As String, ByVal value As Object)
'SRC>         
'SRC>         Dim setName As String
'SRC>         Dim documentPropertySets As Inventor.PropertySets = doc.PropertySets
'SRC> 
'SRC>         'If the property exists as a built-in property, set the value
'SRC>         If PropertyLookup.TryGetValue(propertyName, setName) Then
'SRC>             Try
'SRC>                 documentPropertySets.Item(setName).Item(propertyName).Value = value
'SRC>                 Exit Sub
'SRC>             Catch
'SRC>             End Try
'SRC>             
'SRC>         End If
'SRC> 
'SRC>         'Not found in standard properties, search custom properties
'SRC>         Dim currentPropertySet As Inventor.PropertySet = documentPropertySets.Item("Inventor User Defined Properties")
'SRC>             Try
'SRC>                 currentPropertySet.Item(propertyName).Value = value
'SRC>                 Exit Sub
'SRC>             Catch
'SRC>                 currentPropertySet.Add(value, propertyname)
'SRC>             End Try
'SRC>     End Sub
'SRC> 
'SRC>     Shared Function CustomPropertyExists(currentPropertySet As Inventor.PropertySet, propertyName As String)
'SRC> 
'SRC>         Dim a As Object
'SRC>         Try
'SRC>             a = currentPropertySet.Name(propertyName)
'SRC>             Return True
'SRC>         Catch
'SRC>             Return False
'SRC>         End Try
'SRC>     End Function
'SRC> 
'SRC>     Shared Function PropertySetExists(ByRef doc As Inventor.Document, ByVal propertySetName As String)
'SRC>         For Each PropertySet In doc.PropertySets
'SRC>             If String.Equals(PropertySet.Name, propertySetName, StringComparison.OrdinalIgnoreCase)
'SRC>                 Return True
'SRC>             End If
'SRC>         Next
'SRC>         Return False
'SRC>     End Function
'SRC> 
'SRC>         Shared Sub SetProperty(ByRef doc As Inventor.Document, ByVal propertySetName As String, ByVal propertyName As String, ByVal value As Object)
'SRC>             
'SRC>             Dim documentPropertySets As Inventor.PropertySets = doc.PropertySets
'SRC>             'If the property set exists, set the value, or add it if needed
'SRC>             If PropertySetExists(doc, propertySetName) Then
'SRC>                 Try
'SRC>                     documentPropertySets.Item(propertySetName).Item(propertyName).Value = value
'SRC>                     Exit Sub
'SRC>                 Catch
'SRC>                     documentPropertySets.Item(propertySetName).Add(value, propertyname)
'SRC>                 End Try
'SRC>             
'SRC>             Else
'SRC> 
'SRC>                 'Create the property set, then the property
'SRC>                 Try
'SRC>                     documentPropertySets.Add(propertySetName)
'SRC>                     documentPropertySets.Item(propertySetName).Add(value, propertyname)
'SRC>                 Catch ex As Exception
'SRC> 
'SRC>                 End Try
'SRC>             
'SRC>             End If
'SRC>         End Sub
'SRC> End Class

'
' ============================================================================
' EMBEDDED SOURCE MODULE: stock-number-to-balloon
' Disabled reference source retained inside MASTER for controlled integration.
' ============================================================================
'SRC> '##########################
'SRC> '###   Balloon Update   ###
'SRC> '##########################
'SRC> 'Source: https://github.com/InventorCode/iLogicRules
'SRC> 
'SRC> Sub Main()
'SRC> 
'SRC> 	Dim doc As Inventor.Document = ThisDoc.Document
'SRC> 	Guard.OnlyDrawingDocuments(doc, "This tool is not compatible with this type of file.  Please run from a drawing.")
'SRC> 	FixItemNumbers
'SRC> 
'SRC> End Sub 'Main()'
'SRC> 
'SRC> Sub FixItemNumbers()
'SRC> 
'SRC> 	Dim doc As Inventor.DrawingDocument = ThisDoc.Document
'SRC> 	Dim drawingBoms As Inventor.DrawingBOMs = doc.DrawingBOMs
'SRC> 	Dim drawingBom As Inventor.DrawingBOM
'SRC> 	Dim drawingBomRow As DrawingBOMRow
'SRC> 	Dim bomRow As Inventor.BOMRow
'SRC> 	Dim stockNumber As String
'SRC> 	
'SRC> 	For Each drawingBom In drawingBoms
'SRC> 
'SRC> 		For Each drawingBomRow In drawingBom.DrawingBOMRows
'SRC> 			
'SRC> 			bomRow = drawingBomRow.BOMRow
'SRC> 			stockNumber = GetStockNumber(bomRow)
'SRC> 			Try
'SRC> 				If (IsFabricatedPart(stockNumber)) Then
'SRC> 					bomRow.ItemNumber = GetSheetView(bomRow)
'SRC> 				End If
'SRC> 			Catch
'SRC> 			End Try
'SRC> 		Next
'SRC> 	Next
'SRC> 	
'SRC> End Sub
'SRC> 
'SRC> 
'SRC> Public Function GetStockNumber(ByRef bomRow As Inventor.BOMRow)
'SRC> 
'SRC> 	Dim doc As Inventor.Document = bomRow.ComponentDefinitions(1).Document
'SRC> 	Return PropertyShim.GetProperty(doc, "Stock Number")
'SRC> 
'SRC> End Function
'SRC> 
'SRC> Public Function GetSheetView(ByRef BOMRow As Inventor.BOMRow)
'SRC> 
'SRC> 	Dim doc As Inventor.Document = BOMRow.ComponentDefinitions(1).Document
'SRC> 	Return PropertyShim.GetProperty(doc, "Sheet") & PropertyShim.GetProperty(doc, "View")
'SRC> 
'SRC> End Function
'SRC> 
'SRC> 
'SRC> Public Function IsFabricatedPart(ByRef input As String) As Boolean
'SRC>         Return Text.RegularExpressions.Regex.IsMatch(If(input,"error"), "\b\d{3,4}\-[0123456789]\d\d[a-z|A-Z]*\b")
'SRC> End Function
'SRC> 
'SRC> 
'SRC> Public Class Guard
'SRC> 
'SRC>     Shared Sub OnlyDrawingDocuments(doc As Inventor.Document, message As String)
'SRC>         Dim tempDocument As Inventor.DrawingDocument
'SRC>         Try
'SRC>             tempDocument = doc
'SRC>         Catch ex As Exception
'SRC>             Throw New SystemException(message)
'SRC>         End Try
'SRC>     End Sub
'SRC> 
'SRC> End Class
'SRC> 
'SRC> 
'SRC> Public Class PropertyShim
'SRC> 
'SRC>         Shared ReadOnly PropertyLookup As Dictionary(Of String, String) = New Dictionary(Of String,String)(StringComparer.OrdinalIgnoreCase) From 
'SRC>         {{"Title", "Inventor Summary Information"},
'SRC>         {"Subject", "Inventor Summary Information"},
'SRC>         {"Author", "Inventor Summary Information"},
'SRC>         {"Keywords", "Inventor Summary Information"},
'SRC>         {"Comments", "Inventor Summary Information"},
'SRC>         {"Last Saved By", "Inventor Summary Information"},
'SRC>         {"Revision Number", "Inventor Summary Information"},
'SRC>         {"Thumbnail", "Inventor Summary Information"},
'SRC>         {"Category","Inventor Document Summary Information"},
'SRC>         {"Manager","Inventor Document Summary Information"},
'SRC>         {"Company","Inventor Document Summary Information"},
'SRC>         {"Creation Time","Design Tracking Properties"},
'SRC>         {"Part Number","Design Tracking Properties"},
'SRC>         {"Project","Design Tracking Properties"},
'SRC>         {"Cost Center","Design Tracking Properties"},
'SRC>         {"Checked By","Design Tracking Properties"},
'SRC>         {"Date Checked","Design Tracking Properties"},
'SRC>         {"Engr Approved By","Design Tracking Properties"},
'SRC>         {"Engr Date Approved","Design Tracking Properties"},
'SRC>         {"User Status","Design Tracking Properties"},
'SRC>         {"Material","Design Tracking Properties"},
'SRC>         {"Part Property Revision Id","Design Tracking Properties"},
'SRC>         {"Catalog Web Link","Design Tracking Properties"},
'SRC>         {"Part Icon","Design Tracking Properties"},
'SRC>         {"Description","Design Tracking Properties"},
'SRC>         {"Vendor","Design Tracking Properties"},
'SRC>         {"Document SubType","Design Tracking Properties"},
'SRC>         {"Document SubType Name","Design Tracking Properties"},
'SRC>         {"Proxy Refresh Date","Design Tracking Properties"},
'SRC>         {"Mfg Approved By","Design Tracking Properties"},
'SRC>         {"Mfg Date Approved","Design Tracking Properties"},
'SRC>         {"Cost","Design Tracking Properties"},
'SRC>         {"Standard","Design Tracking Properties"},
'SRC>         {"Design Status","Design Tracking Properties"},
'SRC>         {"Designer","Design Tracking Properties"},
'SRC>         {"Engineer","Design Tracking Properties"},
'SRC>         {"Authority","Design Tracking Properties"},
'SRC>         {"Parameterized Template","Design Tracking Properties"},
'SRC>         {"Template Row","Design Tracking Properties"},
'SRC>         {"External Property Revision Id","Design Tracking Properties"},
'SRC>         {"Standard Revision","Design Tracking Properties"},
'SRC>         {"Manufacturer","Design Tracking Properties"},
'SRC>         {"Standards Organization","Design Tracking Properties"},
'SRC>         {"Language","Design Tracking Properties"},
'SRC>         {"Defer Updates","Design Tracking Properties"},
'SRC>         {"Size Designation","Design Tracking Properties"},
'SRC>         {"Categories","Design Tracking Properties"},
'SRC>         {"Stock Number","Design Tracking Properties"},
'SRC>         {"Weld Material","Design Tracking Properties"},
'SRC>         {"Mass","Design Tracking Properties"},
'SRC>         {"SurfaceArea","Design Tracking Properties"},
'SRC>         {"Volume","Design Tracking Properties"},
'SRC>         {"Density","Design Tracking Properties"},
'SRC>         {"Valid MassProps","Design Tracking Properties"},
'SRC>         {"Flat Pattern Width","Design Tracking Properties"},
'SRC>         {"Flat Pattern Length","Design Tracking Properties"},
'SRC>         {"Flat Pattern Area","Design Tracking Properties"},
'SRC>         {"Sheet Metal Rule","Design Tracking Properties"},
'SRC>         {"Last Updated With","Design Tracking Properties"},
'SRC>         {"Sheet Metal Width","Design Tracking Properties"},
'SRC>         {"Sheet Metal Length","Design Tracking Properties"},
'SRC>         {"Sheet Metal Area","Design Tracking Properties"},
'SRC>         {"Material Identifier","Design Tracking Properties"},
'SRC>         {"Appearance","Design Tracking Properties"},
'SRC>         {"Flat Pattern Defer Update","Design Tracking Properties"}}
'SRC> 
'SRC>         Public Shared PropertySetLookup As HashSet(Of String) = New HashSet(Of String) From {
'SRC>             "Inventor Summary Information",
'SRC>             "Inventor Document Summary Information",
'SRC>             "Design Tracking Properties",
'SRC>             "Inventor User Defined Properties"
'SRC>         }
'SRC> 
'SRC>         ''' <summary>
'SRC>         ''' Return the specified document property's value. This is the short form of this function.
'SRC>         ''' Only requires a document and property propertyName. 
'SRC>         ''' </summary>
'SRC>         ''' <param name="doc">Inventor Document</param>
'SRC>         ''' <param name="propertyName">Name of the Property</param>
'SRC>         ''' <returns></returns>
'SRC>         Shared Function GetProperty(ByRef doc As Inventor.Document, ByVal propertyName As String) As Object
'SRC> 
'SRC>             Dim setName As String
'SRC>             Dim documentPropertySets As Inventor.PropertySets = doc.PropertySets
'SRC>             'Get propertySet for provided propertyName (if exists)
'SRC>             If PropertyLookup.TryGetValue(propertyName, setName) Then
'SRC>                 Return documentPropertySets.Item(setName).Item(propertyName).Value
'SRC>             End If
'SRC> 
'SRC>             'Not found in standard properties, search custom properties
'SRC>             Dim currentPropertySet As Inventor.PropertySet = documentPropertySets.Item("Inventor User Defined Properties")
'SRC>             Try
'SRC>                 Return currentPropertySet.Item(propertyName).Value
'SRC>             Catch
'SRC>             End Try
'SRC> 
'SRC>             'Still not found, search other custom property sets!
'SRC>             If documentPropertySets.Count >= PropertySetLookup.Count Then
'SRC>                 For Each currentPropertySet In doc.PropertySets
'SRC>                     If PropertySetLookup.Contains(currentPropertySet.DisplayName)
'SRC>                         Return ""
'SRC>                     End If
'SRC> 
'SRC>                     Try
'SRC>                         Return currentPropertySet.Item(propertyName).Value
'SRC>                     Catch ex As Exception
'SRC>                         Return ""
'SRC>                     End Try
'SRC>                 Next
'SRC>             End If
'SRC> 
'SRC>             'Still not found, return nothing...
'SRC>             Return ""
'SRC> 
'SRC>         End Function
'SRC> 
'SRC>         Shared Function GetProperty(ByRef doc As Inventor.Document, ByVal setName As String, ByVal propertyName As String) As Object
'SRC> 
'SRC>             Dim documentPropertySets As Inventor.PropertySets = doc.PropertySets
'SRC>             Try
'SRC>                 Dim currentPropertySet As Inventor.PropertySet = documentPropertySets.Item(setName)
'SRC>                 Dim currentProperty As Inventor.Property = currentPropertySet.Item(propertyName)
'SRC>                 Return currentProperty.Value
'SRC>             Catch ex As Exception
'SRC>                 Return ""
'SRC>             End Try
'SRC> 
'SRC>         End Function
'SRC>     Shared Sub SetProperty(ByRef doc As Inventor.Document, ByVal propertyName As String, ByVal value As Object)
'SRC>         
'SRC>         Dim setName As String
'SRC>         Dim documentPropertySets As Inventor.PropertySets = doc.PropertySets
'SRC> 
'SRC>         'If the property exists as a built-in property, set the value
'SRC>         If PropertyLookup.TryGetValue(propertyName, setName) Then
'SRC>             Try
'SRC>                 documentPropertySets.Item(setName).Item(propertyName).Value = value
'SRC>                 Exit Sub
'SRC>             Catch
'SRC>             End Try
'SRC>             
'SRC>         End If
'SRC> 
'SRC>         'Not found in standard properties, search custom properties
'SRC>         Dim currentPropertySet As Inventor.PropertySet = documentPropertySets.Item("Inventor User Defined Properties")
'SRC>             Try
'SRC>                 currentPropertySet.Item(propertyName).Value = value
'SRC>                 Exit Sub
'SRC>             Catch
'SRC>                 currentPropertySet.Add(value, propertyname)
'SRC>             End Try
'SRC>     End Sub
'SRC> 
'SRC>     Shared Function CustomPropertyExists(currentPropertySet As Inventor.PropertySet, propertyName As String)
'SRC> 
'SRC>         Dim a As Object
'SRC>         Try
'SRC>             a = currentPropertySet.Name(propertyName)
'SRC>             Return True
'SRC>         Catch
'SRC>             Return False
'SRC>         End Try
'SRC>     End Function
'SRC> 
'SRC>     Shared Function PropertySetExists(ByRef doc As Inventor.Document, ByVal propertySetName As String)
'SRC>         For Each PropertySet In doc.PropertySets
'SRC>             If String.Equals(PropertySet.Name, propertySetName, StringComparison.OrdinalIgnoreCase)
'SRC>                 Return True
'SRC>             End If
'SRC>         Next
'SRC>         Return False
'SRC>     End Function
'SRC> 
'SRC>         Shared Sub SetProperty(ByRef doc As Inventor.Document, ByVal propertySetName As String, ByVal propertyName As String, ByVal value As Object)
'SRC>             
'SRC>             Dim documentPropertySets As Inventor.PropertySets = doc.PropertySets
'SRC>             'If the property set exists, set the value, or add it if needed
'SRC>             If PropertySetExists(doc, propertySetName) Then
'SRC>                 Try
'SRC>                     documentPropertySets.Item(propertySetName).Item(propertyName).Value = value
'SRC>                     Exit Sub
'SRC>                 Catch
'SRC>                     documentPropertySets.Item(propertySetName).Add(value, propertyname)
'SRC>                 End Try
'SRC>             
'SRC>             Else
'SRC> 
'SRC>                 'Create the property set, then the property
'SRC>                 Try
'SRC>                     documentPropertySets.Add(propertySetName)
'SRC>                     documentPropertySets.Item(propertySetName).Add(value, propertyname)
'SRC>                 Catch ex As Exception
'SRC> 
'SRC>                 End Try
'SRC>             
'SRC>             End If
'SRC>         End Sub
'SRC> End Class
