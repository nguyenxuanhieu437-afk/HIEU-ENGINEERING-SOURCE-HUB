' HIEU TOOL - Sync Drawing Sheet Name with referenced model Part Number
' Works with Autodesk Inventor 2025+ (.idw / Inventor .dwg)
' Each sheet uses the first drawing view with a valid referenced model.
' Empty sheets, missing references and blank Part Numbers are skipped.
' The name matches Part Number exactly; Inventor manages :1, :2 sheet numbers.
'
' Set True to show a report when manually running the rule.
' Set False when attaching the rule to a Before Save event.

Sub Main()
    Const SHOW_REPORT As Boolean = True

    If Not TypeOf ThisDoc.Document Is Inventor.DrawingDocument Then
        MessageBox.Show("Chi chay rule nay trong ban ve Inventor (.idw / .dwg).", _
                        "HIEU - Sync Sheet / Part Number")
        Exit Sub
    End If

    Dim dwg As Inventor.DrawingDocument = CType(ThisDoc.Document, Inventor.DrawingDocument)
    Dim report As New System.Text.StringBuilder()
    Dim renamed As Integer = 0
    Dim unchanged As Integer = 0
    Dim skipped As Integer = 0
    Dim failed As Integer = 0

    For Each sh As Inventor.Sheet In dwg.Sheets
        Dim originalName As String = sh.Name
        Dim sourceDoc As Inventor.Document = Nothing

        If sh.DrawingViews.Count = 0 Then
            skipped += 1
            report.AppendLine("SKIP (no view): " & originalName)
            Continue For
        End If

        ' Find first resolvable model view on this sheet.
        For Each v As Inventor.DrawingView In sh.DrawingViews
            Try
                Dim descriptor As Inventor.DocumentDescriptor = v.ReferencedDocumentDescriptor
                If descriptor IsNot Nothing Then
                    sourceDoc = descriptor.ReferencedDocument
                    If sourceDoc IsNot Nothing Then Exit For
                End If
            Catch
                ' A view can have a missing or unresolvable document reference.
            End Try
        Next

        If sourceDoc Is Nothing Then
            skipped += 1
            report.AppendLine("SKIP (missing model): " & originalName)
            Continue For
        End If

        Try
            Dim propSet As Inventor.PropertySet = sourceDoc.PropertySets.Item("Design Tracking Properties")
            Dim rawValue As Object = propSet.Item("Part Number").Value
            Dim partNumber As String = ""
            If rawValue IsNot Nothing Then partNumber = System.Convert.ToString(rawValue).Trim()

            If partNumber.Length = 0 Then
                skipped += 1
                report.AppendLine("SKIP (blank Part Number): " & originalName)
                Continue For
            End If

            ' Some characters are not suitable for an Inventor sheet name.
            Dim targetBase As String = CleanSheetName(partNumber)
            If targetBase.Length = 0 Then
                skipped += 1
                report.AppendLine("SKIP (invalid Part Number): " & originalName)
                Continue For
            End If

            ' Each sheet uses the exact model Part Number as its base name.
            Dim target As String = targetBase

            ' Inventor browser may display "SheetName:1" instead of "SheetName".
            If String.Equals(GetSheetBaseName(sh.Name), target, System.StringComparison.OrdinalIgnoreCase) Then
                unchanged += 1
                Continue For
            End If

            sh.Name = target
            renamed += 1
            report.AppendLine(originalName & "  ->  " & sh.Name)

        Catch ex As System.Exception
            failed += 1
            report.AppendLine("ERROR: " & originalName & " | " & ex.Message)
        End Try
    Next

    If SHOW_REPORT Then
        Dim summary As String = "Changed: " & renamed & vbCrLf & _
                                "Already matched: " & unchanged & vbCrLf & _
                                "Skipped: " & skipped & vbCrLf & _
                                "Errors: " & failed & vbCrLf & vbCrLf & report.ToString()
        MessageBox.Show(summary, "HIEU - Sync Sheet / Part Number")
    End If
End Sub

Function GetSheetBaseName(fullName As String) As String
    Dim p As Integer = fullName.LastIndexOf(":"c)
    If p >= 0 AndAlso p < fullName.Length - 1 Then
        Dim number As Integer
        If Integer.TryParse(fullName.Substring(p + 1), number) Then
            Return fullName.Substring(0, p)
        End If
    End If
    Return fullName
End Function

Function CleanSheetName(partNumber As String) As String
    Dim value As String = partNumber.Trim()
    Dim invalid As String = "\/:*?""<>|"
    For Each ch As Char In invalid
        value = value.Replace(ch, "-"c)
    Next
    For code As Integer = 0 To 31
        value = value.Replace(ChrW(code), " "c)
    Next
    Return value.Trim()
End Function
